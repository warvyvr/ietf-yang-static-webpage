module example-ietf-ospf-topology {
  yang-version 1.1;
  namespace "urn:ietf:params:xml:ns:yang:example-ietf-ospf-topology";
  prefix "ospft";
  import ietf-yang-types {
    prefix "yang";
  }
  import ietf-network {
    prefix "nd";
  }
  import ietf-network-topology {
    prefix "lnk";
  }
  import ietf-l3-unicast-topology {
    prefix "l3t";
  }
   organization
    "IETF I2RS (Interface to the Routing System) Working Group";
  contact
    "WG Web:    <http://tools.ietf.org/wg/i2rs/>
     WG List:   <mailto:i2rs@ietf.org>
     WG Chair:  Susan Hares
                <mailto:shares@ndzh.com>
     WG Chair:  Russ White
                <mailto:russ@riw.us>
     Editor:    Alexander Clemm
                <mailto:ludwig@clemm.org>
     Editor:    Jan Medved
                <mailto:jmedved@cisco.com>
     Editor:    Robert Varga
                <mailto:robert.varga@pantheon.sk>
     Editor:    Xufeng Liu
                <mailto:xliu@kuatrotech.com>
     Editor:    Nitin Bahadur
                <mailto:nitin_bahadur@yahoo.com>
     Editor:    Hariharan Ananthakrishnan
                <mailto:hari@packetdesign.com>";
  description
    "This module defines a model for OSPF network topologies.
     Copyright (c) 2017 IETF Trust and the persons identified as
     authors of the code.  All rights reserved.
     Redistribution and use in source and binary forms, with or
     without modification, is permitted pursuant to, and subject
     to the license terms contained in, the Simplified BSD License
     set forth in Section 4.c of the IETF Trust's Legal Provisions
     Relating to IETF Documents
     (http://trustee.ietf.org/license-info).
     This version of this YANG module is part of
     draft-ietf-i2rs-yang-l3-topology-08;
     see the RFC itself for full legal notices.
     NOTE TO RFC EDITOR: Please replace above reference to
     draft-ietf-i2rs-yang-l3-topology-08 with RFC
     number when published (i.e. RFC xxxx).";
   revision "2017-01-04" {
    description
      "Initial revision.
       NOTE TO RFC EDITOR: Please replace the following reference
       to draft-ietf-i2rs-yang-l3-topology-08 with
       RFC number when published (i.e. RFC xxxx).";
    reference
      "draft-ietf-i2rs-yang-l3-topology-08";
  }
  typedef area-id-type {
    type yang:dotted-quad;
    description
      "Area ID type.";
  }
  grouping ospf-topology-type {
    description
      "Identifies the OSPF topology type.";
    container ospf {
      presence "indiates OSPF Topology";
      description
        "Its presence identifies the OSPF topology type.";
    }
  }
  augment "/nd:networks/nd:network/nd:network-types/"
    + "l3t:l3-unicast-topology" {
    description
      "Defines the OSPF topology type.";
    uses ospf-topology-type;
  }
  augment "/nd:networks/nd:network/l3t:l3-topology-attributes" {
    when "../nd:network-types/l3t:l3-unicast-topology/ospf" {
      description
        "Augment only for OSPF topology";
    }
    description
      "Augment topology configuration";
    container ospf-topology-attributes {
      description
        "Containing topology attributes";
      leaf area-id {
        type area-id-type;
        description
          "OSPF area ID";
      }
    }
  }
  augment "/nd:networks/nd:network/nd:node/l3t:l3-node-attributes" {
    when "../../nd:network-types/l3t:l3-unicast-topology/ospf" {
      description
        "Augment only for OSPF topology";
    }
    description
      "Augment node configuration";
    uses ospf-node-attributes;
  }
  augment "/nd:networks/nd:network/lnk:link/l3t:l3-link-attributes" {
    when "../../nd:network-types/l3t:l3-unicast-topology/ospf" {
      description
        "Augment only for OSPF topology";
    }
    description
      "Augment link configuration";
    uses ospf-link-attributes;
  }
  grouping ospf-node-attributes {
    description
      "OSPF node scope attributes";
    container ospf-node-attributes {
      description
        "Containing node attributes";
      choice router-type {
        description
          "Indicates router type";
        case abr {
          leaf abr {
            type empty;
            description
              "The node is ABR";
          }
        }
        case asbr {
          leaf asbr {
            type empty;
            description
              "The node is ASBR";
          }
        }
        case internal {
          leaf internal {
            type empty;
            description
              "The node is internal";
          }
        }
        case pseudonode {
          leaf pseudonode {
            type empty;
            description
              "The node is pseudonode";
          }
        }
      }
      leaf dr-interface-id {
        when "../pseudonode" {
          description
            "Valid only for pseudonode";
        }
        type uint32;
        default "0";
        description
          "For pseudonodes, DR interface-id";
      }
      leaf-list multi-topology-id {
        type uint8 {
          range "0..127";
        }
        max-elements "128";
        description
          "List of Multi-Topology Identifier up-to 128 (0-127).
           See RFC 4915";
      }
    }
  }
  grouping ospf-link-attributes {
    description
      "OSPF link scope attributes";
    container ospf-link-attributes {
      description
        "Containing OSPF link attributes";
      leaf multi-topology-id {
        type uint8 {
          range "0..127";
        }
        description "Multi topology ID";
      }
    }
  } // ospf-link-attributes
  augment "/l3t:l3-node-event" {
    description
      "OSPF node event";
    uses ospf-topology-type;
    uses ospft:ospf-node-attributes;
  }
  augment "/l3t:l3-link-event" {
    description
      "OSPF link event";
    uses ospf-topology-type;
    uses ospft:ospf-link-attributes;
  }
}
