module ietf-lisp-itr {
  namespace "urn:ietf:params:xml:ns:yang:ietf-lisp-itr";
  prefix lisp-itr;
  import ietf-lisp {
    prefix lisp;
  }
  import ietf-lisp-address-types {
    prefix lcaf;
  }
  import ietf-inet-types {
    prefix inet;
  }
  organization
    "IETF LISP (Locator/ID Separation Protocol) Working Group";
  contact
    "lisp@ietf.org";
  description
    "This YANG module defines the generic configuration
     data for a LISP ITR. The module can be extended by vendors
     to define vendor-specific configuration parameters and
     policies.
     Copyright (c) 2015 IETF Trust and the persons identified as
     authors of the code.  All rights reserved.
     Redistribution and use in source and binary forms, with or
     without modification, is permitted pursuant to, and subject
     to the license terms contained in, the Simplified BSD License
     set forth in Section 4.c of the IETF Trust's Legal Provisions
     Relating to IETF Documents
     (http://trustee.ietf.org/license-info).
     This version of this YANG module is part of RFC 6338; see
     the RFC itself for full legal notices.
    ";
  revision 2016-06-30 {
    description
      "Initial revision.";
    reference
      "https://tools.ietf.org/html/rfc6830";
  }
  identity itr {
    base lisp:lisp-role;
    description
      "LISP ITR.";
  }
  augment "/lisp:lisp/lisp:lisp-router-instances/"
  + "lisp:lisp-router-instance/lisp:lisp-role" {
    when "lisp:lisp-role-type = 'lisp-itr:itr'" {
      description
        "Augment is valid when LISP role type is ITR.";
    }
    description
      "This augments LISP devices list with ITR specific
       parameters.";
    container itr-cfg {
      presence "LISP ITR operation enabled";
      description
        "ITR configuration";
      container rloc-probing {
        presence "RLOC probing active";
        description
          "RLOC-probing parameters";
        leaf interval {
          type uint16;
          units "seconds";
          description
            "Interval in seconds";
        }
        leaf retries {
          type uint8;
          description
            "Number of retries";
        }
        leaf retries-interval {
          type uint16;
          units "seconds";
          description
            "Interval in seconds between retries";
        }
      }
      leaf itr-rlocs {
        type leafref {
          path "/lisp:lisp/lisp:locator-sets/lisp:locator-set/"
          + "lisp:locator-set-name";
        }
        description
          "Refrence to a locator set that the ITR includes in
           Map-Requests";
      }
      container map-resolvers {
        description
          "The Map-Resolvers configured for the ITR.";
        list map-resolver {
          key "id";
          min-elements 1;
          description
            "List of Map-Resolvers configured for the ITR.";
          leaf id {
            type lisp:eid-id;
            description
              "Id of the EID for which the Map-Server is
               configured.";
          }
          container eid-address {
            uses lcaf:lisp-address;
            description
              "EID for which the Map-Resolver is configured.";
          }
          leaf-list map-resolver-address {
            type inet:ip-address;
            description
              "Map-Resolver RLOC address.";
          }
        }
      }
      container proxy-etrs {
        description
          "Proxy ETRs configured for the ITR.";
        list proxy-etr {
          key "id";
          description
            "List of PETR configured for the ITR.";
          leaf id {
            type lisp:eid-id;
            description
              "Id of the EID for which the PETR is configured.";
          }
          container eid-address {
            uses lcaf:lisp-address;
            description
              "EID for which the PETR is configured.";
          }
          leaf-list proxy-etr-address{
            type inet:ip-address;
            description
              "PETR RLOC address.";
          }
        }
      }
      container map-cache{
        uses lisp:mappings;
        description
          "EID to RLOCs mappings cache.";
      }
      uses lisp:servicing-eids-grouping;
    }
  }
  augment "/lisp:lisp-state/lisp:lisp-router-instances/"
  + "lisp:lisp-router-instance/lisp:lisp-role" {
    when "lisp:lisp-role-type = 'lisp-itr:itr'" {
      description
        "Augment is valid when LISP role type is ITR.";
    }
    description
      "This augments LISP devices list state with ITR specific
       parameters.";
    container itr-state {
      config false;
      description
        "ITR state.";
      container map-cache{
        uses lisp:mappings;
        description
          "EID to RLOCs mappings cache.";
      }
    }
  }
}
