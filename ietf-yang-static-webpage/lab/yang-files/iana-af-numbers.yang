module iana-af-numbers {
   namespace "urn:ietf:params:xml:ns:yang:iana-af-numbers";
   prefix "ianaafn";
   organization
      "IANA";
   contact
      "Postal:    Internet Assigned Numbers Authority
       Internet Corporation for Assigned Names and Numbers
       12025 Waterfront Drive, Suite 300
       Los Angeles, CA 90094-2536
       USA
       Tel:    +1  310-301-5800
       E-Mail: iana&iana.org";
   description
      "The MIB module defines the AddressFamilyNumbers
       textual convention.";
   revision "2017-05-19" {
      description
         "Initial revision.";
      reference
         "IANA-ADDRESS-FAMILY-NUMBERS-MIB";
   }
   identity iana-af-numbers {
      description
         "The definition of this textual convention with the
          addition of newly assigned values is published
          periodically by the IANA, in either the Assigned
          Numbers RFC, or some derivative of it specific to
          Internet Network Management number assignments.
          (The latest arrangements can be obtained by
          contacting the IANA.)
          Requests for new values should be made to IANA via
          email (iana&iana.org).";
   }
   identity ipV4 {
      base iana-af-numbers;
      description
         "IP Version 4";
      reference
         "";
   }
   identity ipV6 {
      base iana-af-numbers;
      description
         "IP Version 6";
      reference
         "";
   }
   identity nsap {
      base iana-af-numbers;
      description
         "NSAP";
      reference
         "";
   }
   identity hdlc {
      base iana-af-numbers;
      description
         "8-bit multidrop";
      reference
         "";
   }
   identity bbn1822 {
      base iana-af-numbers;
      description
         "";
      reference
         "";
   }
   identity all802 {
      base iana-af-numbers;
      description
         "includes all 802 media plus Ethernet
          'canonical format'";
      reference
         "";
   }
   identity e163 {
      base iana-af-numbers;
      description
         "";
      reference
         "";
   }
   identity e164 {
      base iana-af-numbers;
      description
         "SMDS, Frame Relay, ATM";
      reference
         "";
   }
   identity f69 {
      base iana-af-numbers;
      description
         "Telex";
      reference
         "";
   }
   identity x121 {
      base iana-af-numbers;
      description
         "X.25, Frame Relay";
      reference
         "";
   }
   identity ipx {
      base iana-af-numbers;
      description
         "IPX (Internet Protocol Exchange)";
      reference
         "";
   }
   identity appleTalk {
      base iana-af-numbers;
      description
         "Apple Talk";
      reference
         "";
   }
   identity decnetIV {
      base iana-af-numbers;
      description
         "DEC Net Phase IV";
      reference
         "";
   }
   identity banyanVines {
      base iana-af-numbers;
      description
         "Banyan Vines";
      reference
         "";
   }
   identity e164withNsap {
      base iana-af-numbers;
      description
         "E.164 with NSAP format subaddress";
      reference
         "";
   }
   identity dns {
      base iana-af-numbers;
      description
         "Domain Name System";
      reference
         "";
   }
   identity distinguishedName {
      base iana-af-numbers;
      description
         "Distinguished Name, per X.500";
      reference
         "";
   }
   identity asNumber {
      base iana-af-numbers;
      description
         "16-bit quantity, per the AS number space";
      reference
         "";
   }
   identity xtpOverIpv4 {
      base iana-af-numbers;
      description
         "XTP over IP version 4";
      reference
         "";
   }
   identity xtpOverIpv6 {
      base iana-af-numbers;
      description
         "XTP over IP version 6";
      reference
         "";
   }
   identity xtpNativeModeXTP {
      base iana-af-numbers;
      description
         "XTP native mode XTP";
      reference
         "";
   }
   identity fibreChannelWWPN {
      base iana-af-numbers;
      description
         "Fibre Channel World-Wide Port Name";
      reference
         "";
   }
   identity fibreChannelWWNN {
      base iana-af-numbers;
      description
         "Fibre Channel World-Wide Node Name";
      reference
         "";
   }
   identity gwid {
      base iana-af-numbers;
      description
         "Gateway Identifier";
      reference
         "";
   }
   identity afi {
      base iana-af-numbers;
      description
         "AFI for L2VPN information";
      reference
         "";
   }
   identity mplsTpSectionEndpointIdentifier {
      base iana-af-numbers;
      description
         "MPLS-TP Section Endpoint Identifier";
      reference
         "";
   }
   identity mplsTpLspEndpointIdentifier {
      base iana-af-numbers;
      description
         "MPLS-TP LSP Endpoint Identifier";
      reference
         "";
   }
   identity mplsTpPseudowireEndpointIdentifier {
      base iana-af-numbers;
      description
         "MPLS-TP Pseudowire Endpoint Identifier";
      reference
         "";
   }
   identity eigrpCommonServiceFamily {
      base iana-af-numbers;
      description
         "EIGRP Common Service Family";
      reference
         "";
   }
   identity eigrpIpv4ServiceFamily {
      base iana-af-numbers;
      description
         "EIGRP IPv4 Service Family";
      reference
         "";
   }
   identity eigrpIpv6ServiceFamily {
      base iana-af-numbers;
      description
         "EIGRP IPv6 Service Family";
      reference
         "";
   }
   identity lispCanonicalAddressFormat {
      base iana-af-numbers;
      description
         "LISP Canonical Address Format (LCAF)";
      reference
         "";
   }
   identity bgpLs {
      base iana-af-numbers;
      description
         "BGP-LS";
      reference
         "";
   }
   identity fortyeightBitMacBitMac {
      base iana-af-numbers;
      description
         "48-bit MAC";
      reference
         "";
   }
   identity sixtyfourBitMac {
      base iana-af-numbers;
      description
         "64-bit MAC";
      reference
         "";
   }
   identity oui {
      base iana-af-numbers;
      description
         "Organizationally Unique Identifier";
      reference
         "";
   }
   identity mac24 {
      base iana-af-numbers;
      description
         "MAC/24";
      reference
         "";
   }
   identity mac40 {
      base iana-af-numbers;
      description
         "MAC/40";
      reference
         "";
   }
   identity ipv664 {
      base iana-af-numbers;
      description
         "IPv6/64";
      reference
         "";
   }
   identity rBridgePortID {
      base iana-af-numbers;
      description
         "RBridge Port ID";
      reference
         "";
   }
   identity trillNickname {
      base iana-af-numbers;
      description
         "TRILL Nickname";
      reference
         "";
   }
}
