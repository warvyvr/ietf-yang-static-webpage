module ietf-connectionless-oam-methods {
namespace "urn:ietf:params:xml:ns:yang:ietf-connectionless-oam-methods";
 prefix coam-methods;

 import ietf-interfaces {
  prefix if;
 }
 import ietf-connectionless-oam {
  prefix coam;
 }

  organization
    "IETF LIME Working Group";
  contact
    "Deepak Kumar dekumar@cisco.com
     Qin Wu       bill.wu@huawei.com
     S Raghavan   srihari@cisco.com
     Zitao Wang   wangzitao@huawei.com
     R Rahman     rrahman@cisco.com";
  description
    "This YANG module defines the RPCs for ,
     connectionless OAM to be used within IETF
     in a protocol Independent manner.
     Functional level abstraction is indendent with
     YANG modeling. It is assumed that each protocol maps
     corresponding abstracts to its native format.
     Each protocol may extend the YANG model defined
     here to include protocol specific extensions";

  revision 2017-05-18 {
    description
      "02 version";
    reference "draft-ietf-lime-yang-connectionless-oam-methods";
  }

  rpc continuity-check {
    if-feature "coam:continuity-check";
    description
      "Generates continuity-check as per RFC7276.";
    input {
      container destination-tp {
        uses coam:tp-address;
        description
          "Destination test point.";
      }
      uses coam:session-type;
      leaf source-interface {
        type if:interface-ref;
        description
          "Source interface.";
      }
      leaf outbound-interface {
        type if:interface-ref;
        description
          "Outbound interface.";
      }
      leaf count {
        type uint32;
        default "5";

        description
          "Specifies the number of
           packets that will be sent.";
      }
      leaf vrf {
        type coam:routing-instance-ref;
        description
          "VRF instance.";
      }
      leaf ttl {
        type uint8;
        default "255";
        description
          "Time to live (TTL).";
      }
      leaf packet-size {
        type uint32 {
          range "64..10000";
        }
        default "64";
        description
          "Size of ping echo request
           packets, in octets";

      }
    }
    output {
      list error-code-list {
        key "response-index";
        leaf response-index {
          type uint32;
          description
            "Response index.";
        }
        leaf status-code {
          type int32;
          description
            "Error code is ";
        }
        leaf status-sub-code {
          type uint8;
          description
            "Sub code.";
        }
        description
          "Error code list.";
      }
      uses coam:continuity-check-data;
    }

  }

  rpc path-discovery {
    if-feature "coam:path-discovery";
    description
      "Generates path discovery as per RFC7276.";
    input {
      container destination-tp {
        uses coam:tp-address;
        description
          "Destination test point.";
      }
      uses coam:session-type;
      leaf source-interface {
        type if:interface-ref;
        description
          "Source interface.";
      }
      leaf outbound-interface {
        type if:interface-ref;
        description
          "Outbound interface.";

      }
      leaf vrf {
        type coam:routing-instance-ref;
        description
          "VRF";
      }
      leaf max-ttl {
        type uint8;
        default "255";
        description
          "Max ttl.";
      }
    }
    output {
      list response-list {
        key "response-index";
        description
          "Path discovery response list.";
        leaf response-index {
          type uint32;
          description
            "Response index.";
        }
        leaf status-code {
          type int32;
          description

            "Error code is ";
        }
        leaf status-sub-code {
          type uint8;
          description
            "Sub code is ";
        }
      }
      uses coam:path-discovery-data;
    }
  }
}
