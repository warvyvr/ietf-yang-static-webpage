module ietf-flexi-grid-ted {
  yang-version 1.1;

  namespace "urn:ietf:params:xml:ns:yang:ietf-flexi-grid-ted";
  prefix "fg-ted";

  import ietf-network {
    prefix "nd";
  }

  import ietf-network-topology {
    prefix "lnk";
  }

  import ietf-te-topology {
    prefix "tet";
  }

   import ietf-inet-types {
      prefix "inet";
   }

  organization
         "IETF CCAMP Working Group";

      contact
         "Editor: Jorge E. Lopez de Vergara
                  <jorge.lopez_vergara@uam.es>";

      description
         "This module contains a collection of YANG definitions for
         a Flexi-Grid Traffic Engineering Database (TED).

         Copyright (c) 2017 IETF Trust and the persons identified as
         authors of the code.  All rights reserved.

         Redistribution and use in source and binary forms, with or
         without modification, is permitted pursuant to, and subject
         to the license terms contained in, the Simplified BSD
         License set forth in Section 4.c of the IETF Trust's Legal
         Provisions Relating to IETF Documents
         (http://trustee.ietf.org/license-info).";

      revision 2017-03-01 {
         description
            "version 4.";

         reference
             "RFC XXX: A Yang Data Model for
             Flexi-Grid Optical Networks ";
      }

   typedef flexi-grid-trasponder-type {
         type enumeration {
             enum "flexi-grid-transponder" {
                description
                   "Flexi-grid transponder";
             }
             enum "flexi-grid-sliceable-transponder" {
                description
                   "Flexi-grid sliceable transponder";
             }
         }
         description "Determines the trasponder type:
             flexi-grid-transponder or
             flexi-grid-sliceable-transponder";
   }

  typedef modulation {
         type enumeration {
            enum QPSK {
                description
                "QPSK (Quadrature Phase Shift Keying) modulation";
                }
            enum DP_QPSK {
                description "DP-QPSK (Dual Polarization Quadrature
                Phase Shift Keying) modulation";
                }
            enum QAM16 {
                description "QAM16 (Quadrature Amplitude Modulation
                - 4 bits per symbol) modulation";
                }

            enum DP_QAM16 {
                description "DP-QAM16 (Dual Polarization
                Quadrature Amplitude Modulation - 4 bits per
                symbol) modulation";
                }
            enum DC_DP_QAM16 {
                description "DC DP-QAM16 (Dual Polarization
                Quadrature Amplitude Modulation - 4 bits per
                symbol) modulation";
                }
         }
         description
            "Enumeration that defines the type of wave modulation";
   }

   typedef FEC {
         type enumeration {
            enum reed-solomon {
                description "Reed-Solomon error correction";
            }
            enum hamming-code{
                description "Hamming Code error correction";
            }
            enum golay{
                description "Golay error correction";
            }
         }
         description "Enumeration that defines the type of
         Forward Error Correction";
   }

   typedef interface-type {
         type enumeration {
            enum numbered-interface {
                description "The interface is numbered";
            }
            enum unnumbered-interface {
                description "The interface is unnumbered";
            }
         }
         description
            "Enumeration that defines if an interface is numbered or
            unnumbered";
   }

   /*
      Typedef related to references
   */
      typedef flexi-grid-link-ref {
         type leafref {
            path
               "/nd:networks/nd:network/lnk:link/lnk:link-id";
         }

         description
            "This type is used by data models that need to reference
            a flexi-grid optical link.";
      }

      typedef flexi-grid-node-port-ref {
         type leafref {
            path "/nd:networks/nd:network/nd:node/tet:te/tet:config/"
            +"fg-ted:interfaces/fg-ted:port-number";
         }
         description
            "This type is used by data models that need to reference
            a flexi-grid port.";
      }

      typedef flexi-grid-transponder-ref {
         type leafref {
            path "/nd:networks/nd:network/nd:node/tet:te/"+
            "tet:tunnel-termination-point/tet:tunnel-tp-id";
         }
         description
            "This type is used by data models that need to reference
            a trasponder.";
      }

   grouping flexi-grid-network-type {
         container flexi-grid-network {
            presence "indicates a flexi-grid optical network";
            description "flexi-grid optical network";
         }
         description "If present, it indicates a flexi-grid
         optical TED network";
   }

   grouping flexi-grid-node-attributes-config {
         description "Set of attributes of an optical node.";

         list interfaces {
            key "name";
            unique "port-number";
            description "List of interfaces contained in the node";
            leaf name {
               type string;
               description "Interface name";
            }

            leaf port-number {
               type uint32;
               description "Number of the port used by the interface";
            }
            leaf input-port {
               type boolean;
               description "Determines if the port is an input port";
            }
            leaf output-port {
               type boolean;
               description
               "Determines if the port is an output port";
            }
            leaf description {
               type string;
               description "Description of the interface";
            }
            leaf type {
               type interface-type;
               description "Determines the type of the interface";
            }
            container numbered-interface {
               when "../fg-ted:type =
               'numbered-interface'" {
                 description
                 "If the interface is a numbered interface";
               }
               description "Container that defines an numbered
               interface with an ip-address";
               leaf n-i-ip-address{
                  type inet:ip-address;
                  description "IP address of the numbered interface";
               }
            }
            container unnumbered-interface {
               when "../fg-ted:type =
               'unnumbered-interface'" {
                 description
                   "If the interface is an unnumbered interface";
               }
               description "Container that defines an unnumbered
               interface with an ip-address and a label";
               leaf u-i-ip-address{
                  type inet:ip-address;
                  description "IP address of the interface";
               }
               leaf label {
                  type uint32;
                  description "Number as label for the interface";
               }
            }
         }
      }

   grouping flexi-grid-node-attributes-state {
         description "Flexigrid node attributes (state).";
   }
   grouping flexi-grid-link-attributes-config {
         description "Set of attributes of an optical link";
            leaf-list available-label-flexi-grid {
               type bits {
                  bit is-available{
                    description "Set to 1 when it is available";
                  }
               }
               description
                  "Array of bits that determines whether a spectral
                  slot is available or not.";
            }

            leaf N-max {
               type int32;
               description "Maximum number of channels available.";
            }

            leaf base-frequency {
               type decimal64 {
                  fraction-digits 5;
               }
               units THz;
               default 193.1;
               description "Default central frequency";
               reference "rfc7698";
            }
            leaf nominal-central-frequency-granularity {
               type decimal64 {
                  fraction-digits 5;
               }
               units GHz;
               default 6.25;
               description
                  "It is the spacing between allowed nominal central
                  frequencies and it is set to 6.25 GHz";
               reference "rfc7698";
            }

            leaf slot-width-granularity {
               type decimal64 {
                  fraction-digits 5;
               }
               units GHz;
               description "Minimum space between slot widths";
               reference "rfc7698";
            }
   }

   grouping flexi-grid-link-attributes-state {
      description "Flexigrid link attributes (state)";
   }
   grouping flexi-grid-transponder-attributes-config {
      description "Configuration of an optical transponder";
      leaf-list available-modulation {
         type modulation;
         description
            "List determining all the available modulations";
      }
      leaf modulation-type {
         type modulation;
         description "Modulation type of the wave";
      }
      leaf-list available-FEC {
         type FEC;
         description "List determining all the available FEC";
      }
      leaf FEC-enabled {
         type boolean;
         description
            "Determines whether the FEC is enabled or not";
      }
      leaf FEC-type {
         type FEC;
         description "FEC type of the transponder";
      }
   }

   grouping flexi-grid-transponder-attributes-state {
      description "State of an optical transponder";
   }

   grouping flexi-grid-sliceable-transponder-attributes-config {
      description
         "Configuration of a sliceable transponder.";
      list transponder-list {
         key "carrier-id";
         description "List of carriers";
         leaf carrier-id {
            type uint32;
            description "Identifier of the carrier";
         }
      }
   }

   grouping flexi-grid-sliceable-transponder-attributes-state {
      description "State of a sliceable transponder.";
      uses flexi-grid-transponder-attributes-state;
   }

   grouping flexi-grid-connectivity-matrix-attributes {
      description "Connectivity matrix between the input and
          output ports";
      list connections {
         key "input-port-id";
         leaf input-port-id {
            type flexi-grid-node-port-ref;
            description "Identifier of the input port";
         }
         leaf output-port-id {
            type flexi-grid-node-port-ref;
            description "Identifier of the output port";
         }
         description "List of connections between input and
          output ports";
      }
   }

   augment "/nd:networks/nd:network/nd:network-types" {
            uses flexi-grid-network-type;
             description "Augment network-types including flexi-grid
             topology";
   }

  augment "/nd:networks/nd:network/lnk:link/tet:te/tet:config" {
    when "/nd:networks/nd:network/nd:network-types/
  fg-ted:flexi-grid-network" {
      description "Augment only for Flexigrid network.";
    }
    description "Augment link configuration";
    uses flexi-grid-link-attributes-config;
  }

  augment "/nd:networks/nd:network/lnk:link/tet:te/tet:state" {
    when "/nd:networks/nd:network/nd:network-types/
  fg-ted:flexi-grid-network" {
      description "Augment only for Flexigrid network.";
    }
    description "Augment link state";
    uses flexi-grid-link-attributes-config;
    uses flexi-grid-link-attributes-state;
  }

   augment "/nd:networks/nd:network/nd:node/tet:te/tet:config"  {
      when "/nd:networks/nd:network/nd:network-types/
    fg-ted:flexi-grid-network" {
         description "Augment only for Flexigrid network.";
      }
      uses flexi-grid-node-attributes-config;
      description "Augment node config with flexi-grid attributes";
   }

   augment "/nd:networks/nd:network/nd:node/tet:te/tet:state"  {
      when "/nd:networks/nd:network/nd:network-types/
    fg-ted:flexi-grid-network" {
         description "Augment only for Flexigrid network.";
      }
      uses flexi-grid-node-attributes-config;
      uses flexi-grid-node-attributes-state;
      description "Augment node config with flexi-grid attributes";
   }

   augment "/nd:networks/nd:network/nd:node/tet:te/tet:config"+
         "/tet:te-node-attributes/tet:connectivity-matrix" {
       when "/nd:networks/nd:network/nd:network-types/
     fg-ted:flexi-grid-network" {
          description "Augment only for Flexigrid network.";
       }

      uses flexi-grid-connectivity-matrix-attributes;
      description "Augment node connectivity-matrix for node config";
    }

    augment "/nd:networks/nd:network/nd:node/tet:te/tet:state"+
         "/tet:te-node-attributes/tet:connectivity-matrix" {
       when "/nd:networks/nd:network/nd:network-types/
     fg-ted:flexi-grid-network"{
          description "Augment only for Flexigrid network.";
       }

      uses flexi-grid-connectivity-matrix-attributes;
      description "Augment node connectivity-matrix for node config";
    }

   augment "/nd:networks/nd:network/nd:node/tet:te"+
      "/tet:tunnel-termination-point" {
      when "/nd:networks/nd:network/nd:network-types/
    fg-ted:flexi-grid-network"{
          description "Augment only for Flexigrid network.";
       }

       leaf transponder-type {
            type flexi-grid-trasponder-type;
            description "Type of flexi-grid transponder";
      }
        container state {
          description "State of the transponder";
        }
        container config {
          description "Configuration of the transponder";
        }
       description "Augment node with configuration and state
       for transponder";
   }

   augment "/nd:networks/nd:network/nd:node/tet:te"+
          "/tet:tunnel-termination-point/fg-ted:config" {
      when "../fg-ted:transponder-type" {
          description "When it is either a flexi-grid transponder
           or a sliceable transponder";
      }
      uses flexi-grid-transponder-attributes-config;
      description "Augment node state with transponder attributes";
   }

   augment "/nd:networks/nd:network/nd:node/tet:te"+
          "/tet:tunnel-termination-point/fg-ted:state" {
      when "../fg-ted:transponder-type"{
          description "When it is either a flexi-grid transponder
           or a sliceable transponder";
      }
      uses flexi-grid-transponder-attributes-state;
      uses flexi-grid-transponder-attributes-config;
      description "Augment node state with transponder attributes";
   }

   augment "/nd:networks/nd:network/nd:node/tet:te"+
          "/tet:tunnel-termination-point/fg-ted:config" {
      when "../fg-ted:transponder-type =
        'flexi-grid-sliceable-transponder'"{
          description
              "When it is a flexi-grid sliceable transponder";
      }
      uses flexi-grid-sliceable-transponder-attributes-config;
      description "Augment node with sliceable transponder
          attributes";
   }

   augment "/nd:networks/nd:network/nd:node/tet:te"+
          "/tet:tunnel-termination-point/fg-ted:state" {
      when "../fg-ted:transponder-type =
      'flexi-grid-sliceable-transponder'"{
          description
              "When it is a flexi-grid sliceable transponder";
    }
    uses flexi-grid-sliceable-transponder-attributes-state;
    uses flexi-grid-sliceable-transponder-attributes-config;
    description "Augment node with sliceable transponder
        attributes";
   }
}
