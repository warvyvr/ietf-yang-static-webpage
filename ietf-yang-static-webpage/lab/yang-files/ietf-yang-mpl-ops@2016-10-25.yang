module ietf-yang-mpl-ops {
  yang-version 1;
  namespace
      "urn:ietf:params:xml:ns:yang:ietf-yang-mpl-ops";
  prefix mpl;
  organization
    "IETF ROLL (Routing over Low power and lossy networks)
 Working Group";
  contact
     "WG Web:   http://tools.ietf.org/wg/roll/
     WG List:  mailto:roll@ietf.org
     WG Chair: Peter van der Stok
               mailto:consultancy@vanderstok.org
     WG Chair: Ines Robles
               mailto:maria.ines.robles@ericsson.com
     Editor:   Peter van der Stok
               mailto:consultancy@vanderstok.org";
  description
    "This module contains information about the operation of
the MPL protocol.
     Copyright (c) 2016 IETF Trust and the persons identified as
     authors of the code.  All rights reserved.
     Redistribution and use in source and binary forms, with or
     without modification, is permitted pursuant to, and subject
     to the license terms contained in, the Simplified BSD License
     set forth in Section 4.c of the IETF Trust's Legal Provisions
     Relating to IETF Documents
     (http://trustee.ietf.org/license-info).
     This version of this YANG module is part of RFC XXXX; see
     the RFC itself for full legal notices.";
revision "2016-10-25" {
      description "Initial revision.";
      reference
        "I-D:draft-ietf-roll-mpl-yang: A YANG model for Multicast
 Protocol for Low power and lossy Networks (MPL)";
    }
    container mpl-ops {
      description
        "Parameter settings for each MPL server and for each
individual domain of the server.";
      leaf SE_LIFETIME {
        type uint16;
        description
           "lifetime in milliseconds/(mpl timer units),
             equivalent to SEED_SET_ENTRY_LIFETIME/TUNIT as
            specified in RFC7774.";
      }
      leaf PROACTIVE_FORWARDING {
        type boolean;
        description
          "The boolean value indicates whether the MPL forwarder
           schedules MPL data message transmission after
            receiving them for the first time.";
      }
      leaf SEED_SET_ENTRY_LIFETIME {
         type uint64;
         description
           "The value indicates the minimum lifetime for an entry
            in the Seed set expressed in seconds. Default value
            is 30 minutes.";
       }
       list mpl-parameter{
       key  domainID;
       description
          "Each domain has a set of MPL forwarding parameters
           which regulate the forwarding operation.";
       leaf  domainID{
       type uint16;
       description
           "Each domainID must be present in
mpl-parameter list.";
       }
       leaf DATA_MESSAGE_IMIN{
       type uint16;
       description
            "The minimum Trickle timer interval, as defined in
             [RFC6206], for MPL Data Message transmissions.";
        }
        leaf DATA_MESSAGE_IMAX{
        type uint16;
        description
             "The maximum Trickle timer interval, as defined in
             [RFC6206], for MPL Data Message transmissions.";
        }
        leaf DATA_MESSAGE_K{
        type uint16;
        default 1;
        description
           "The redundancy constant, as defined in [RFC6206], for
            MPL Data Message transmissions.";
        }
        leaf DATA_MESSAGE_TIMER_EXPIRATIONS{
        type uint16;
        default 3;
        description
           "The number of Trickle timer expirations that occur
            before terminating the Trickle algorithm's
            retransmission of a given MPL Data Message.";
         }
         leaf CONTROL_MESSAGE_IMIN{
         type uint16;
         description
            "The minimum Trickle timer interval, as defined
             in [RFC6206], for MPL Control Message
             transmissions.";
         }
         leaf CONTROL_MESSAGE_IMAX{
         type uint16;
         description
            "The maximum Trickle timer interval, as defined
            in [RFC6206], for MPL Control Message
             transmissions.";
         }
         leaf CONTROL_MESSAGE_K{
         type uint16;
         default 1;
         description
            "The redundancy constant, as defined in [RFC6206],
             for MPL Control Message transmissions.";
         }
         leaf CONTROL_MESSAGE_TIMER_EXPIRATIONS{
         type uint16;
         default 10;
         description
            "The number of Trickle time expirations that occur
              before terminating the Trickle algorithm
              for MPL Control Message transmissions.";
          }
       }  // list MPL-parameter
     }  // container MPL-ops
} // module ietf-yang-mpl-ops
