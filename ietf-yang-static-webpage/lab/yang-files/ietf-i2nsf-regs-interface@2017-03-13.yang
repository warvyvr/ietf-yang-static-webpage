module ietf-i2nsf-regs-interface {
  namespace
    "urn:ietf:params:xml:ns:yang:ietf-i2nsf-regs-interface";
  prefix
    regs-interface;
  import ietf-inet-types{
    prefix inet;
  }
  organization
    "IETF I2NSF (Interface to Network Security Functions)
     Working Group";
  contact
    "WG Web: <http://tools.ietf.org/wg/i2nsf>
     WG List: <mailto:i2nsf@ietf.org>
     WG Chair: Adrian Farrel
     <mailto:Adrain@olddog.co.uk>
     WG Chair: Linda Dunbar
     <mailto:Linda.duhbar@huawei.com>
     Editor: Sangwon Hyun
     <mailto:swhyun77@skku.edu>
     Editor: Jaehoon Paul Jeong
     <mailto:pauljeong@skku.edu>
     Editor: Yunsuk Yeo
     <mailto:yunsuk@imtl.skku.ac.kr>
     Editor: Sanguk Woo
     <mailto:suwoo@imtl.skku.ac.kr>
     Editor: Susan Hares
     <mailto:shares@ndzh.com>";
  description
    "It defines a YANG data module for Registration Interface.";
  revision "2017-03-13"{
    description "Initial revision";
    reference
      "draft-hares-i2nsf-capability-data-model-01
       draft-hyun-i2nsf-registration-interface-im-01";
  }
  grouping i2nsf-nsf-performance-caps {
    description
      "NSF performance capabbilities";
    leaf cpu-num {
      type uint16;
      description
        "cpu-num";
    }
    leaf disk-size {
      type uint16;
      description
        "disk-size";
    }
    leaf ram-size {
      type uint16;
      description
        "ram-size";
    }
  }
  grouping i2nsf-nsf-profile {
    description
      "Detail information of an NSF";
    container performance-capability {
      description
        "Performance Capability";
      uses i2nsf-nsf-performance-caps;
    }
    container i2nsf-capability {
      description
        "We will use draft-hares-i2nsf-capability-data-model-00.txt
         later";
    }
  }
  grouping i2nsf-nsf-access-info {
    description
      "NSF access information";
    leaf nsf-address {
      type inet:ipv4-address;
      mandatory true;
      description
        "nsf-address";
    }
    leaf nsf-port-number {
      type inet:port-number;
      description
        "nsf-port-number";
    }
  }
  grouping i2nsf-regs-req {
    description
      "The capability information of newly created NSF to notify its
       capability to Security Controller";
    container nsf-profile {
      description
        "NSF Profile";
      uses i2nsf-nsf-profile;
    }
    container nsf-access-info {
      description
        "NSF Access Info";
      uses i2nsf-nsf-access-info;
    }
  }
  grouping i2nsf-life-cycle-mgnt-req {
    description
      "Rquired information for req-creation-type and
       req-elimination-type";
    leaf req-level {
      type uint16;
      description
        "req-level";
    }
    leaf req-id {
      type uint64;
      mandatory true;
      description
        "req-id";
    }
    choice req-type {
      description
        "req-type";
      case req-creation-type {
        description
          "req-creation-type";
        container nsf-profile {
          description
           "NSF Profile";
          uses i2nsf-nsf-profile;
        }
      }
      case req-elimination-type {
        description
          "req-elimination-type";
        container nsf-access-info {
          description
            "NSF Access Info";
          uses i2nsf-nsf-access-info;
        }
      }
    }
  }
}
