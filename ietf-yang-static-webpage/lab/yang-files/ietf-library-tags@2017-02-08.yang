module ietf-library-tags {
  // namespace
  namespace "urn:ietf:params:xml:ns:yang:ietf-library-tags";
  prefix ylibtags;
  import ietf-yang-library {
     prefix yanglib;
  }
  import ietf-module-tags {
     prefix mtags;
  }
  // meta
  organization "IETF NetMod Working Group (NetMod)";
  contact
      "NetMod Working Group - <netmod@ietf.org>";
  description
    "This module augments ietf-yang-library with searchable
    classfication tags.  Tags may be IANA or privately defined
    types.";
  revision "2017-02-06" {
    description
      "Initial revision.";
    reference "RFC TBD";
  }
  augment "/yanglib:modules-state/yanglib:module" {
    description
      "The yang library structure is augmented with a module tags
       list. This allows operators to tag modules regardless of
       whether the modules included tag support or not";
    uses mtags:module-tags;
  }
}
