module ietf-savi-fcfs {
    namespace "urn:ietf:params:xml:ns:yang:ietf-savi-fcfs";
    prefix savi-fcfs;
    import ietf-yang-types {
        prefix yang;
    }
    import ietf-inet-types {
        prefix inet;
    }
    import ietf-interfaces {
        prefix if;
    }

    import ietf-savi {
        prefix savi;
    }
    organization "IETF SAVI Working Group";
    contact
        "
        WG Web:  <http://datatracker.ietf.org/wg/savi/charter>
        Editor:   Changqing An
                  <mailto:acq@tsinghua.edu.cn>
        ";
    description
        "
        The Yang data module defined for SAVI FCFS.
        ";

    revision 2017-02-15 {
        description "Initial revision.";
        reference "DRAFT XXX: A YANG Data Model for SAVI Management";
    }

     /* Identities */

    identity savi-fcfs-state {
        base savi:binding-state;
        description "Base identity for the sates definition of SAVI FCFS.";
    }
    identity tentative {
        base savi-fcfs-state;
        description "A state defined in SAVI FCFS.";
    }
    identity valid {

        base savi-fcfs-state;
        description "A state defined in SAVI FCFS.";
    }
    identity testing_vp {
        base savi-fcfs-state;
        description "A state defined in SAVI FCFS.";
    }
    identity testing_vp-lt {
        base savi-fcfs-state;
        description "A state defined in SAVI FCFS.";
    }

     /* State data */

    augment "/savi:savi-state/savi:savi-instances/savi:savi-instance" {
        when "/savi:savi/savi:savi-instances/savi:savi-instance/savi:savi-method = 'savi-fcfs'";
        description "Binding state table specific for SAVI FCFS.";
        container binding-state-table {
            description "Binding state table specific for SAVI FCFS.";
            list binding-state-entry {
                key "ifname address";
                description "A binding status entry specific for SAVI FCFS.";
                leaf address {
                    type inet:ipv6-address;
                    description "The binding source IP address.";
                }
                uses savi:binding-entry;
                leaf state {
                    type identityref {
                        base savi-fcfs-state;
                    }
                    description "State of the entry as defined in SAVI FCFS: NO_BIND, TENTATIVE, VALID, TESTING_VP, TESTING_TP-LT";
                }
            }
        }
    }

     /* Configuration Data */

    augment "/savi:savi/savi:savi-instances/savi:savi-instance" {
        when "/savi:savi/savi:savi-instances/savi:savi-instance/savi:savi-method = 'savi-fcfs'";
        description "Parameters specific to SAVI FCFS.";
        container params {
            description "Parameters specific to SAVI FCFS.";
            leaf tent_lt {
                type yang:timeticks;
                default 50;
                description "A default value defined in SAVI FCFS.";

                reference "TENT_LT from [RFC6620].";
            }

            leaf default_lt {
                type yang:timeticks;
                default 30000;
                description "A default value defined in SAVI FCFS.";
                reference "DEFAULT_LT from [RFC6620]";
            }

            leaf twait {
                type yang:timeticks;
                default 25;
                description "A default value defined in SAVI FCFS";
                reference "T_WAIT from [RFC6620].";
            }
            container if-attributes {
                description "Interface attributes specific to SAVI SEND.";
                list if-attribute {
                    key ifname;
                        description "A list of attributes for each interface.";
                    leaf ifname {
                        type if:interface-ref;
                        description "The name of the interface.";
                    }
                    leaf validating {
                        type boolean;
                        must .=not(../trust);
                        default true;
                        description "SAVI FCFS processing is performed in the port.";
                    }

                    leaf trust {
                        type boolean;
                        must .=not(../validating);
                        default false;
                        description "SAVI FCFS processing is not performed in the port.";
                    }
                } //list
            } //container
        } //container
    } //augment
}
