module example-ietf-ippm-udp-latency {
  namespace "urn:example:ietf-ippm-udp-latency";
  prefix "ippm-udp-latency";
  import ietf-inet-types {
    prefix inet;
  }
  import ietf-lmap-control {
    prefix "lmapc";
  }
  import ietf-lmap-report {
    prefix "lmapr";
  }
  grouping ippm-udp-latency-parameter-grouping {
    leaf src-ip {
      type inet:ip-address;
      description
        "The source IP address of the UDP measurement traffic.";
    }
    leaf src-port {
      type inet:port-number;
      description
        "The source port number of the UDP measurement traffic.";
    }
    leaf dst-ip {
      type inet:ip-address;
      description
        "The destination IP address of the UDP measurement traffic.";
    }
    leaf dst-port {
      type inet:port-number;
      description
        "The destination port number of the UDP measurement traffic.";
    }
    leaf poisson-lambda {
      type decimal64 {
        fraction-digits 4;
      }
      units "seconds";
      default 1.0000;
      description
        "The average interval for the poisson stream with a resolution
         of 0.0001 seconds (0.1 ms).";
    }
    leaf poisson-limit {
      type decimal64 {
        fraction-digits 4;
      }
      units "seconds";
      default 30.0000;
      description
        "The upper limit on the poisson distribution with a resolution
         of 0.0001 seconds (0.1 ms).";
    }
  }
  augment "/lmapc:lmap/lmapc:schedules/lmapc:schedule/lmapc:action"
        + "/lmapc:parameters/lmapc:extension" {
    description
      "This augmentation adds parameters specific to IPPM UDP
       latency metrics to actions.";
    case "ietf-ippm-udp-latency" {
      uses ippm-udp-latency-parameter-grouping;
    }
  }
  augment "/lmapr:report/lmapr:input/lmapr:result"
        + "/lmapr:parameters/lmapr:extension" {
    description
      "This augmentation adds parameters specific to IPPM UDP
       latency metrics to reports.";
    case "ietf-ippm-udp-latency" {
      uses ippm-udp-latency-parameter-grouping;
    }
  }
}
