module ietf-pcp-proxy {
  namespace "urn:ietf:params:xml:ns:yang:ietf-pcp-proxy";
  prefix pcp-proxy;
  import ietf-inet-types { prefix inet; }
  import ietf-pcp { prefix pcp; }
  organization "xxxx Working Group";
  contact
     "Mohamed Boucadair <mohamed.boucadair@orange.com>
      Christian Jacquenet <christian.jacquenet@orange.com>";
  description
       "This module contains a collection of YANG definitions for
        PCP proxy implementations.
        Copyright (c) 2016 IETF Trust and the persons identified as
        authors of the code.  All rights reserved.
        Redistribution and use in source and binary forms, with or
        without modification, is permitted pursuant to, and subject
        to the license terms contained in, the Simplified BSD License
        set forth in Section 4.c of the IETF Trust's Legal Provisions
        Relating to IETF Documents
        (http://trustee.ietf.org/license-info).
        This version of this YANG module is part of RFC XXXX; see
        the RFC itself for full legal notices.";
  revision 2015-08-05 {
      description "Changes xxxx.";
       reference "xxxx";
   }
/*
  *PCP Configuration
  */
    container pcp-proxy-config {
       description
         "PCP proxy";
       leaf enable {
            type boolean;
            description
               "Enable/Disable PCP proxy";
       }
    leaf description {
      type string;
      description
        "Associated a description with the module.";
    }
      container pcp-proxy-instances {
           description
             "PCP proxy instances";
            list pcp-proxy-instance {
                key "id";
                  description
                    "PCP proxy instance";
               leaf id {
                  type uint32;
                  description
                   "An identifier of the PCP proxy instance";
               }
               leaf name {
                  type string;
                  description
                   "A name of the PCP proxy instance";
               }
               list version {
                  key version;
                  description
                   "Supported PCP versions.";
                  uses pcp:pcp-version;
               }
               list pcp-servers {
                  key "pcp-server-id";
                  description
                   "List of provisioned PCP servers.";
                  uses pcp:pcp-server-address;
               }
               leaf authentication-enable {
                  type boolean;
                  description
                   "Enable/disable PCP authentication.";
               }
                container opcode-configuration {
                    description
                   "Opcode-related configuration";
                    uses pcp:opcode;
                    leaf relay-unknown-opcode {
                       type boolean;
                       description
                           "The proxy can be instructed to relay
                             or to reject unknown opcodes.";
                    }
                    }
                }
                container option-configuration {
                    description
                      "Option-related configuration";
                    uses pcp:option;
                    leaf relay-mandatory-unknown-option {
                       type boolean;
                       description
                          "The proxy can be instructed to relay or
                            to reject mandatory unknown options.";
                    }
                    leaf relay-optionnal-unknown-option {
                       type boolean;
                       description
                          "The proxy can be instructed to relay or
                            to reject optional unknown options.";
                    }
                }
               leaf terminate-proxy-recursion {
                  type boolean;
                  description
                          "The proxy can be instructed to terminate
                            proxy recursion.";
               }
               container mapping-table {
                  description
                    "PCP mapping table maintained by the PCP proxy";
                    list mapping-entry {
                      key "index";
                      description
                        "PCP mapping entry";
                      uses pcp:mapping-entry;
                      leaf local-assigned-ip-address {
                            type inet:ipv6-prefix;
                            description
                               "If the local PCP-controlled function
                                 alters the source IP address, this
                                 information must be stored.";
                      }
                      container local-assigned-port {
                            description
                                "If the local PCP-controlled function
                                  alters the source port, this
                                  information must be stored.";
                            uses pcp:port-number;
                      }
                   }
                }
            }
        }
/*
 * PCP state
 */
 container pcp-proxy-state {
    config false;
        description
          "PCP proxy";
        container pcp-proxy-instances {
            description
                "PCP proxy Instances";
            list pcp-proxy-instance {
                key "id";
                description
                  "PCP proxy Instance";
                leaf id {
                    type int32;
                    description
                        "Identifier";
                }
                leaf name {
                    type string;
                    description
                     "Name of the PCP proxy Instance";
                }
               list supported-version {
                  key version;
                  description
                   "List of supported versions";
                  uses pcp:pcp-version;
               }
               leaf preferred-version {
                  type uint8;
                  description
                   "Configured preferred version";
               }
         list pcp-proxy-ip-address {
               key address-id;
               description
                  "List of configured addresses to the
                    PCP proxy instance.";
               leaf address-id {
                  type uint32;
                  description
                    "An identifier";
               }
               leaf pcp-proxy-ip-address {
                  type inet:ipv6-address;
                  description
                   "An address";
               }
         }
         list pcp-server-address {
            key "pcp-server-id";
            description
             "list of provisioned PCP servers.";
            uses pcp:pcp-server-address-status;
         }
         leaf authentication-support {
            type boolean;
            description
              "Indicates whether PCP authentication is
                enabled/disabled.";
         }
         container pcp-controlled-function-capability {
            description
               "list of controlled local functions.";
            uses pcp:pcp-controlled-function;
         }
         container opcode-capability {
             description
              "Opcode-related capabilities.";
             uses pcp:opcode;
             leaf relay-unknown-opcode {
                 type boolean;
                 description
                  "instruction related to the processing of unknown
                    opcodes.";
             }
         }
         container option-capability {
                   description
                    "Option-related capabilities.";
                    uses pcp:option;
                    leaf relay-mandatory-unknown-option {
                       type boolean;
                       description
                          "instruction related to the processing
                            of mandatory unknown options.";
                    }
                    leaf relay-optionnal-unknown-option {
                       type boolean;
                       description
                           "instruction related to the processing
                             of optional unknown options.";
                    }
         }
                container opcode-configuration {
                   description
                      "opcode-related configurations.";
                    uses pcp:opcode;
                }
                container option-configuration {
                    description
                      "opcode-related configurations.";
                    uses pcp:option;
                    leaf relay-mandatory-unknown-option {
                        type boolean;
                       description
                             "instruction related to the processing
                               of mandatory unknown options.";
                    }
                    leaf relay-optionnal-unknown-option {
                       type boolean;
                       description
                            "instruction related to the processing
                              of optional unknown options.";
                    }
                }
                leaf authentication-enabled {
                    type boolean;
                    description
                     "status of the PCP authentication activation";
                }
               leaf terminate-proxy-recursion-status {
                    type boolean;
                    description
                     "Indicates whether recursion is
                       terminated or not";
               }
               container mapping-table {
                    description
                        "mapping table";
                    list mapping-entry {
                        key "index";
                        description
                            "mapping entry";
                        uses pcp:mapping-entry;
                      leaf local-assigned-ip-address {
                            type inet:ipv6-prefix;
                            description
                             "An address assigned locally by
                              the proxy";
                      }
                      container local-assigned-port {
                            description
                             "a port assigned locally by the proxy";
                            uses pcp:port-number;
                      }
                      uses pcp:status-code;
                    }
                }
               container traffic-statistics {
                    description
                        "traffic statistics";
                    container client-facing-interface {
                        description
                            "traffic statistics in the client-facing
                              interface";
                        uses pcp:traffic-stat;
                    }
                    container server-facing-interface {
                        description
                            "traffic statistics in the server-facing
                              interface";
                        uses pcp:traffic-stat;
                    }
                    container mapping-table {
                        description
                            "mapping table statistics";
                        uses pcp:mapping-table-stats;
                    }
                }
            }
        }
    }
}
