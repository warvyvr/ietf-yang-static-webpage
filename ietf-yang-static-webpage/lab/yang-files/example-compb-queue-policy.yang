module example-compb-queue-policy {
  yang-version 1;
  namespace "urn:ietf:params:xml:ns:yang:example-compb-queue-policy";
  prefix queue-plcy;
  import ietf-qos-classifier {
    prefix classifier;
  }
  import ietf-qos-policy {
    prefix policy;
  }
  organization "Company B";
  contact
    "Editor:   XYZ
              <mailto:xyz@compb.com>";
  description
    "This module defines a queue policy. The classification
     is based on aforwarding class, and the actions are queues.
     Copyright (c) 2014 IETF Trust and the persons identified as
     authors of the code.  All rights reserved.
     Redistribution and use in source and binary forms, with or
     without modification, is permitted pursuant to, and subject
     to the license terms contained in, the Simplified BSD License
     set forth in Section 4.c of the IETF Trust's Legal Provisions
     Relating to IETF Documents
     (http://trustee.ietf.org/license-info).
     This version of this YANG module is part of RFC XXXX; see
     the RFC itself for full legal notices.";
  revision 2015-04-07 {
    description
      "Latest revision of diffserv policy";
    reference "RFC XXXX";
  }
  identity forwarding-class {
    base classifier:filter-type;
    description
       "Forwarding class filter type";
  }
  grouping forwarding-class-cfg {
    leaf forwarding-class-cfg {
      type string;
      description
        "forwarding-class name";
    }
    description
      "Forwarding class filter";
  }
  augment "/policy:policies" +
          "/policy:policy-entry" +
          "/policy:classifier-entry" +
          "/policy:filter-entry" {
    /* Does NOT support "logical-not" of forwarding class.
       Use "must"? */
    choice filter-params {
      description
        "Choice of filters";
      case forwarding-class-cfg {
        uses forwarding-class-cfg;
        description
          "Filter Type Internal-loss-priority";
      }
    }
    description
      "Augments Diffserv Classifier with fwd class filter";
  }
  identity compb-queue {
    base policy:action-type;
    description
      "compb-queue action type";
  }
  grouping compb-queue-name {
    container queue-name {
      leaf name {
        type string;
        description
          "Queue class name";
      }
      description
        "compb queue container";
    }
    description
      "compb-queue grouping";
  }
  augment "/policy:policies" +
          "/policy:policy-entry" +
          "/policy:classifier-entry" +
          "/policy:classifier-action-entry-cfg" {
    choice action-cfg-params {
      description
        "Choice of action types";
      case compb-queue {
        uses compb-queue-name;
      }
    }
    description
      "Augment the queue actions to queue policy entry";
  }
}
