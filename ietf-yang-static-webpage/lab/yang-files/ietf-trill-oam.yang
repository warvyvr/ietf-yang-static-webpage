module ietf-trill-oam {
     namespace "urn:ietf:params:xml:ns:yang:ietf-trill-oam";
     prefix trilloam;
     import ietf-conn-oam {
       prefix goam;
     }
     import ietf-inet-types {
       prefix inet;
     }
     import ietf-interfaces {
       prefix if;
     }
     import ietf-yang-types {
       prefix yang;
     }
     organization "IETF TRILL Working Group";
     contact
       "
        WG List: mailto:trill@ietf.org
        Editor: Deepak Kumar dekumar@cisco.com";
     description
       "This YANG module defines the configuration for TRILL,
        OAM Fault Management statistics and rpc";
     revision 2016-07-17 {
       description
         "Initial revision.";
       reference "draft-ietf-trill-yang-oam";
     }
    identity trill {
       base goam:technology-types;
       description
         "trill type";
     }
     typedef oam-counter32 {
       type yang:zero-based-counter32;
       description
         "defines 32 bit counter for OAM";
     }
     typedef tril-rb-nickname {
       type uint16;
       description
        "Trill Rbridge Nickname";
     }
     typedef flow-entropy-trill {
       type binary {
         length "1..96";
       }
       description
         "Flow entropy as defined in RFC7455";
     }
     typedef vlan {
       type uint16 {
         range "0..4095";
       }
       description
         "Vlan Identifier.";
     }
     typedef fgl {
       type uint32;
       description
         "Fine Grain Label";
     }
     identity trill-mtv {
       base goam:command-sub-type;
       description
         "identfies this command as multicast tree verification comand";
     }
     identity trill-ping {
       base goam:command-sub-type;
       description
         "identifies the command as TRILL Loopback Request";
     }
     identity trill-trace-route {
       base goam:command-sub-type;
       description
         "identifies the command as TRILL Pathtrace Request.";
     }
     grouping command-ext-trill {
       description
         "group the rpc command extensions for trill";
       choice out-of-band {
         case ipv4-address {
           leaf ipv4-address {
             type inet:ipv4-address;
             description
               "ip version 4 address of the device where out of
                band reply should be sent.";
           }
         }
         case ipv6-address {
           leaf ipv6-address {
             type inet:ipv6-address;
             description
               "ip version 6 address of the device where out of
                band reply should be sent.";
           }
         }
         case trill-nickname {
           leaf trill-nickname {
             type tril-rb-nickname;
             description
               "TRILL Rbridge Nickname of the device where out of
                band reply should be sent.";
           }
         }
         description
           "presence of this node indicate out of band request needed";
       }
       leaf diagnostic-vlan {
         type boolean;
         description
           "indicates whether to include diagnostic VLAN/fgl TLV or not
            in the request.  actual value is the VLAN/FGL specified
            in the command";
       }
     }
     grouping monitor-stats-trill {
       leaf tx-packt-count {
         type oam-counter32;
         description
           "Transmitted Packet count";
       }
       leaf rx-packet-count {
         type oam-counter32;
         description
           "Received packet count, zero for one way message (CCM).";
       }
       leaf min-delay {
         type oam-counter32;
         units milliseconds;
         description
           "Delay is specified in milliseconds, zero for one
            way message (CCM).";
       }
       leaf average-delay {
         type oam-counter32;
         units millisecond;
         description
           "average delay in milliseconds, zero for one way
            message (CCM).";
       }
       leaf max-delay {
         type oam-counter32;
         units millisecond;
         description
           "Maximum delay in milliseconds, zero for one way
            message (CCM).";
       }
       description
         "Monitor Statistics";
   }
   augment "/goam:domains/goam:domain/goam:MAs/goam:MA/goam:MEP/goam:mep-address" {
       case mep-address-trill {
         leaf mep-address-trill {
           when "/goam:domains/goam:domain/goam:technology='trill'" {
             description
              "Technology TRILL";
           }
           type tril-rb-nickname;
           description
            "MEP Address TRILL Rbridge Nickname.";
         }
       }
       description
         "Extend Generic OAM Maintenance Point Address.";
     }
     augment "/goam:domains/goam:domain/goam:MAs/goam:MA/goam:connectivity-context" {
       case connectivity-context-vlan {
         leaf connectivity-context-vlan {
           type vlan;
           description
             "Connectivity context Vlan Identifier.";
         }
       }
       case connectivity-context-fgl {
         leaf connectivity-context-fgl {
           type fgl;
           description
            "connectivity context Fine Grain Label.";
         }
       }
       description
         "Extends connectivity context.";
     }
     augment "/goam:domains/goam:domain/goam:MAs/goam:MA" {
       leaf flow-entropy-trill {
         type flow-entropy-trill;
         description
           "connectivity context flow entropy.";
       }
       description
         "Extends Flow Entropy.";
     }
     augment
   "/goam:domains/goam:domain/goam:MAs/goam:MA/goam:MEP" {
       leaf flow-entropy-trill {
         type flow-entropy-trill;
         description
           "Flow Entropy TRILL";
       }
       description
         "Extends Flow Entropy defined under Generic OAM MEP.";
     }
     augment
   "/goam:domains/goam:domain/goam:MAs/goam:MA/goam:MEP/goam:session" {
       leaf flow-entropy-trill {
         type flow-entropy-trill;
         description
           "Flow Entropy TRILL";
       }
       description
         "Extends Flow Entropy defined under Generic OAM Session.";
     }
     augment "/goam:continuity-check/goam:input" {
       uses command-ext-trill;
       description
         "Extends continuity check input.";
     }
     augment "/goam:continuity-check/goam:input" {
       leaf flow-entropy-trill {
         type flow-entropy-trill;
         description
           "Flow Entropy TRILL";
       }
       description
         "Extends continuity check input Flow entropy.";
     }
     augment "/goam:continuity-check/goam:output" {
       description
         "adds trill specific items on the response";
       leaf upstream-rbridge {
         type tril-rb-nickname;
         description
           "Trill Rbridge nickname.";
       }
       leaf-list next-hop-rbridge {
         type tril-rb-nickname;
         description
           "nickname of the next hop RBRdige";
       }
     }
    augment "/goam:continuity-verification/goam:input" {
       uses command-ext-trill;
       description
         "Extends continuity check input.";
     }
     augment "/goam:continuity-verification/goam:input" {
       leaf flow-entropy-trill {
         type flow-entropy-trill;
         description
           "Flow Entropy TRILL";
       }
       description
         "Extends continuity check input Flow entropy.";
     }
     augment "/goam:continuity-verification/goam:output" {
       description
         "adds trill specific items on the response";
       case monitor-stats-resp {
         uses monitor-stats-trill;
       }
       leaf upstream-rbridge {
         type tril-rb-nickname;
         description
           "Trill Rbridge nickname.";
       }
       leaf-list next-hop-rbridge {
         type tril-rb-nickname;
         description
           "nickname of the next hop RBRdige";
       }
     }
 augment "/goam:traceroute/goam:input" {
       uses command-ext-trill;
       description
          "Extends path disovery Input.";
     }
     augment "/goam:traceroute/goam:input" {
       leaf flow-entropy-trill {
         type flow-entropy-trill;
         description
           "Flow entropy TRILL.";
       }
       description
         "Extends path discovery input flow entropy.";
     }
     augment "/goam:traceroute/goam:output/goam:response" {
       description
         "adds trill specific items on the response";
       case monitor-stats-ext {
         uses monitor-stats-trill; 
       }
       leaf upstream-rbridge {
         type tril-rb-nickname;
         description
           "Upstream Rbridge nickname.";
       }
       leaf-list next-hop-rbridge {
         type tril-rb-nickname;
         description
           "nickname of the next hop RBRdige";
       }
     }
     rpc mtv {
       description
         "Generates Trace-route and return response. Starts with TTL
          of one and increment by one at each hop. Untill destination
          reached or TTL reach max valune";
       input {
         uses goam:maintenance-domain-id {
           description
             "Specifies the MA-domain";
         }
         uses goam:ma-identifier {
           description
             "identfies the Maintenance association";
         }
         uses command-ext-trill {
           description
             "defines extensions needed for trill.
              We are using this structure so mtv command is in line
              with ping and trace-route";
         }
         choice flow-entropy {
           case flow-entropy-null {
             leaf flow-entropy-null {
               type empty;
               description
                 "Empty flow entropy";
             }
           }
           case flow-entropy-trill {
             leaf flow-entropy-trill {
               type flow-entropy-trill;
               description
                 "Flow Entroy TRILL";
             }
           }
           description
             "Flow Entropy choices.";
         }
         leaf max-hop-count {
           type uint8;
           default "255";
           description
             "Defines maximum value of hop count";
         }
         leaf type {
           type identityref {
             base goam:command-sub-type;
           }
           description
             "defines different command types";
         }
         leaf-list scope {
           type tril-rb-nickname;
           description
             "This list contain rbridges that needed to respond
              Empty list indicate all Rbridges needed to respond";
           reference "RFC7455";
         }
         leaf ecmp-choice {
           type enumeration {
             enum "ecmp-use-platform-hash" {
               value 0;
               description
                 "Use Platform hashing to send packet on
                  specified interface.";
             }
             enum "ecmp-use-round-robin" {
               value 1;
               description
                 "Use round robin hashing.";
             }
           }
           description
             "Ecmp Choice enumeration.";
         }
         list outgoing-interfaces {
           key "interface";
           leaf interface {
             type if:interface-ref;
             description
               "Interface";
           }
           description
             "List of Outgoing Interface.";
         }
         container source-mep {
           uses goam:mep-address;
           description
             "Source MEP Container.";
           leaf mep-id {
             type tril-rb-nickname;
             description
               "Trill Rbridge Nickname";
           }
         }
         container destination-mep {
           uses goam:mep-address;
           leaf mep-id {
             type tril-rb-nickname;
             description
               "MEP Identifier.";
           }
           description
            "Destination MEP Identifier.";
         }
       }
       output {
         list response {
           key "mep-address mep-id";
           leaf hop-count {
             type uint8;
             description
               "unsigned integer 1-255";
           }
           leaf mep-id {
             type tril-rb-nickname;
             description
               "Maintenance Endpoint Identifier.";
           }
           leaf mep-address {
             type tril-rb-nickname;
             description
               "Maintenance Endpoint Address.";
           }
           leaf-list next-hop-rbridge {
             type tril-rb-nickname;
             description
               "list of downstream rbridges. There is no perticular
   order";
           }
           leaf upstream-rbridge {
             type tril-rb-nickname;
             description
               "Upstream Rbridge Nickname.";
           }
           leaf multicast-receiver-count {
             type uint32;
             description
               "number of ports that are interested in this multicast
   stream";
           }
           uses monitor-stats-trill;
           description
             "Output list.";
         }
       }
     }
}
