module example-ds-ephemeral {
  yang-version 1.1;
  namespace "urn:example:ds-ephemeral";
  prefix eph;
  import ietf-datastores {
    prefix ds;
  }
  import ietf-origin {
    prefix or;
  }
  // add datastore identity
  identity ds-ephemeral {
    base ds:datastore;
    description
      "The 'ephemeral' datastore.";
  }
  // add origin identity
  identity or-ephemeral {
    base or:dynamic;
    description
      "Denotes data from the ephemeral dynamic datastore.";
  }
  // define ephemeral extension
  extension ephemeral {
    argument "value";
    description
      "This extension is mixed into config false YANG nodes to
       indicate that they are writable nodes in the 'ephemeral'
       datastore.  This statement takes a single argument
       representing a boolean having the values 'true' and
       'false'.  The default value is 'false'.";
  }
}
