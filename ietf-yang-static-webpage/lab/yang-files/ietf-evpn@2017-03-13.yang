module ietf-evpn {
  namespace "urn:ietf:params:xml:ns:yang:ietf-evpn";
  prefix "evpn";
  import ietf-inet-types {
    prefix "inet";
  }
  import ietf-yang-types {
    prefix "yang";
  }
  import ietf-l2vpn {
    prefix "l2vpn";
  }
  import ietf-routing-types {
    prefix "rt-types";
  }
  organization  "ietf";
  contact       "ietf";
  description   "evpn";
  revision "2017-03-13" {
    description " - Added an augment to base L2VPN model to " +
                "   reference an EVPN instance " +
                " - Reused ietf-routing-types.yang " +
                "   vpn-route-targets grouping instead of " +
                "   defining it in this module " +
                "";
    reference   "";
  }
  revision "2016-07-08" {
    description " - Added operational state" +
                " - Added a configuration knob to enable/disable " +
                "   underlay-multicast " +
                " - Added a configuration knob to enable/disable " +
                "   flooding of unknonw unicast " +
                " - Added several configuration knobs " +
                "   to manage ARP and ND" +
                "";
    reference   "";
  }
  revision "2016-06-23" {
    description "WG document adoption";
    reference   "";
  }
  revision "2015-10-15" {
    description "Initial revision";
    reference   "";
  }
  feature evpn-bgp-params {
    description "EVPN's BGP parameters";
  }
  feature evpn-pbb-params {
    description "EVPN's PBB parameters";
  }
  /* Typedefs */
  typedef evpn-instance-ref {
    type leafref {
      path "/evpn/evpn-instances/evpn-instance/name";
    }
    description "A leafref type to an EVPN instance";
  }
  /* Groupings */
  grouping route-rd-rt-grp {
    description "A grouping for a route's route distinguishers " +
                "and route targets";
    list rd-rt {
      key "route-distinguisher";
      leaf route-distinguisher {
        type rt-types:route-distinguisher;
        description "Route distinguisher";
      }
      list vpn-target {
        key "route-target";
        leaf route-target {
          type rt-types:route-target;
          description "BGP route target";
        }
        description "A list of route targets";
      }
      description "A list of route distinguishers and " +
                  "corresponding VPN route targets";
    }
  }
  grouping next-hop-label-grp {
    description "next-hop-label-grp";
    leaf next-hop {
      type inet:ip-address;
      description "next-hop";
    }
    leaf label {
      type rt-types:mpls-label;
      description "label";
    }
  }
  grouping next-hop-label2-grp {
    description "next-hop-label2-grp";
    leaf label2 {
      type rt-types:mpls-label;
      description "label2";
    }
  }
  grouping path-detail-grp {
    description "path-detail-grp";
    container detail {
      config false;
      description "path details";
      container attributes {
        leaf-list extended-community {
          type string;
          description "extended-community";
        }
        description "attributes";
      }
      leaf bestpath {
        type empty;
        description "Indicate this path is the best path";
      }
    }
  }
  /* EVPN YANG Model */
  container evpn {
    description "evpn";
    container common {
      description "common epn attributes";
      choice replication-type {
        description "A choice of replication type";
        case ingress-replication {
          leaf ingress-replication {
            type boolean;
            description "ingress-replication";
          }
        }
        case p2mp-replication {
          leaf p2mp-replication {
            type boolean;
            description "p2mp-replication";
          }
        }
      }
    }
    container evpn-instances {
      description "evpn-instances";
      list evpn-instance {
        key "name";
        description "An EVPN instance";
        leaf name {
          type string;
          description "Name of EVPN instance";
        }
        leaf evi {
          type uint32;
          description "evi";
        }
        container pbb-parameters {
          if-feature "evpn-pbb-params";
          description "PBB parameters";
          leaf source-bmac {
            type yang:hex-string;
            description "source-bmac";
          }
        }
        container bgp-parameters {
          description "BGP parameters";
          container common {
            description "BGP parameters common to all pseudowires";
            list rd-rt {
              if-feature evpn-bgp-params;
              key "route-distinguisher";
              leaf route-distinguisher {
                type rt-types:route-distinguisher;
                description "Route distinguisher";
              }
              uses rt-types:vpn-route-targets;
              description "A list of route distinguishers and " +
                          "corresponding VPN route targets";
            }
          }
        }
        leaf arp-proxy {
          type boolean;
          default false;
          description "Enable (TRUE) or disable (FALSE) ARP proxy";
        }
        leaf arp-suppression {
          type boolean;
          default false;
          description "Enable (TRUE) or disable (FALSE) " +
                      "ARP suppression";
        }
        leaf nd-proxy {
          type boolean;
          default false;
          description "Enable (TRUE) or disable (FALSE) ND proxy";
        }
        leaf nd-suppression {
          type boolean;
          default false;
          description "Enable (TRUE) or disable (FALSE) " +
                      "ND suppression";
        }
        leaf underlay-multicast {
          type boolean;
          default false;
          description "Enable (TRUE) or disable (FALSE) " +
                      "underlay multicast";
        }
        leaf flood-unknown-unicast-supression {
          type boolean;
          default false;
          description "Enable (TRUE) or disable (FALSE) " +
                      "flood unknown unicast suppression";
        }
      }
    }
  }
  container evpn-state {
    description "EVPN operational state";
    container evpn-instances-state {
      config false;
      description "evpn-instances-state";
      list evpn-instance {
        description "The state of an EVPN instance";
        leaf name {
          type string;
          description "Name of EVPN instance";
        }
        leaf evi {
          type uint32;
          description "evi";
        }
        container pbb-parameters {
          if-feature "evpn-pbb-params";
          description "PBB parameters";
          leaf source-bmac {
            type yang:hex-string;
            description "source-bmac";
          }
        }
        container bgp-parameters {
          description "BGP parameters";
          container common {
            description "BGP parameters common to all pseudowires";
            list rd-rt {
              if-feature evpn-bgp-params;
              key "route-distinguisher";
              leaf route-distinguisher {
                type rt-types:route-distinguisher;
                description "Route distinguisher";
              }
              uses rt-types:vpn-route-targets;
              description "A list of route distinguishers and " +
                          "corresponding VPN route targets";
            }
          }
        }
        leaf advertise-mac-suppression-enabled {
          type boolean;
          description "advertise-mac-suppression " +
                      "is enabled (TRUE) " +
                      "or disabled (FALSE)";
        }
        leaf arp-proxy-enabled {
          type boolean;
          description "arp-proxy is enabled (TRUE) " +
                      "or disabled (FALSE)";
        }
        leaf arp-suppression-enabled {
          type boolean;
          description "arp-suppression is enabled (TRUE) " +
                      "or disabled (FALSE)";
        }
        leaf nd-proxy-enabled {
          type boolean;
          description "nd-proxy is enabled (TRUE) " +
                      "or disabled (FALSE)";
        }
        leaf nd-suppression-enabled {
          type boolean;
          description "nd-suppression is enabled (TRUE) " +
                      "or disabled (FALSE)";
        }
        leaf underlay-multicast-enabled {
          type boolean;
          description "underlay-multicast is enabled (TRUE) " +
                      "or disabled (FALSE)";
        }
        leaf flood-unknown-unicast-suppression-enabled {
          type boolean;
          description "flood-unknown-unicast-suppression is " +
                      "enabled (TRUE) or disabled (FALSE)";
        }
        container routes {
          description "routes";
          list ethernet-auto-discovery-route {
            uses route-rd-rt-grp;
            leaf ethernet-segment-identifier {
              type uint32;
              description "Ethernet segment identifier (esi)";
            }
            leaf ethernet-tag {
              type uint32;
              description "An ethernet tag (etag) indentifying a " +
                          "broadcast domain";
            }
            list path {
              uses next-hop-label-grp;
              uses path-detail-grp;
              description "path";
            }
            description "ethernet-auto-discovery-route";
          }
          list mac-ip-advertisement-route {
            uses route-rd-rt-grp;
            leaf ethernet-segment-identifier {
              type uint32;
              description "Ethernet segment identifier (esi)";
            }
            leaf ethernet-tag {
              type uint32;
              description "An ethernet tag (etag) indentifying a " +
                          "broadcast domain";
            }
            leaf mac-address {
              type yang:hex-string;
              description "Route mac address";
            }
            leaf mac-address-length {
              type uint8 {
                range "0..48";
              }
              description "mac address length";
            }
            leaf ip-prefix {
              type inet:ip-prefix;
              description "ip-prefix";
            }
            list path {
              uses next-hop-label-grp;
              uses next-hop-label2-grp;
              uses path-detail-grp;
              description "path";
            }
            description "mac-ip-advertisement-route";
          }
          list inclusive-multicast-ethernet-tag-route {
            uses route-rd-rt-grp;
            leaf ethernet-segment-identifier {
              type uint32;
              description "Ethernet segment identifier (esi)";
            }
            leaf originator-ip-prefix {
              type inet:ip-prefix;
              description "originator-ip-prefix";
            }
            list path {
              uses next-hop-label-grp;
              uses path-detail-grp;
              description "path";
            }
            description "inclusive-multicast-ethernet-tag-route";
          }
          list ethernet-segment-route {
            uses route-rd-rt-grp;
            leaf ethernet-segment-identifier {
              type uint32;
              description "Ethernet segment identifier (esi)";
            }
            leaf originator-ip-prefix {
              type inet:ip-prefix;
              description "originator ip-prefix";
            }
            list path {
              leaf next-hop {
                type inet:ip-address;
                description "next-hop";
              }
              uses path-detail-grp;
              description "path";
            }
            description "ethernet-segment-route";
          }
          list ip-prefix-route {
            uses route-rd-rt-grp;
            leaf ethernet-segment-identifier {
              type uint32;
              description "Ethernet segment identifier (esi)";
            }
            leaf ip-prefix {
              type inet:ip-prefix;
              description "ip-prefix";
            }
            list path {
              uses next-hop-label-grp;
              uses path-detail-grp;
              description "path";
            }
            description "ip-prefix route";
          }
        }
        container statistics {
          description "Statistics";
          leaf tx-count {
            type uint32;
            description "transmission count";
          }
          leaf rx-count {
            type uint32;
            description "receive count";
          }
          container detail {
            description "Detailed statistics";
            leaf broadcast-tx-count {
              type uint32;
              description "broadcast transmission count";
            }
            leaf broadcast-rx-count {
              type uint32;
              description "broadcast receive count";
            }
            leaf multicast-tx-count {
              type uint32;
              description "multicast transmission count";
            }
            leaf multicast-rx-count {
              type uint32;
              description "multicast receive count";
            }
            leaf unicast-tx-count {
              type uint32;
              description "unicast transmission count";
            }
            leaf unicast-rx-count {
              type uint32;
              description "unicast receive count";
            }
          }
        }
      }
    }
  }
  /* augments */  
  augment "/l2vpn:l2vpn/l2vpn:l2vpn-instances" +
          "/l2vpn:l2vpn-instance" {
    description "Augment for an L2VPN instance and EVPN association";
    leaf evpn-instance {
      type evpn-instance-ref;
      description "Reference to an EVPN instance";
    }
  }
  augment "/l2vpn:l2vpn-state" {
    description "Augment for an L2VPN instance's operational " +
                "state of L2VPN and EVPN association";
    leaf evpn-instance {
      type string;
      description "Name of the associated EVPN instance";
    }
  }
}
