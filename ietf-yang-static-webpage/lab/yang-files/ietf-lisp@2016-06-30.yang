module ietf-lisp {
  namespace "urn:ietf:params:xml:ns:yang:ietf-lisp";
  prefix lisp;
  import ietf-interfaces {
    prefix if;
  }
  import ietf-lisp-address-types {
    prefix lcaf;
  }
  organization
    "IETF LISP (Locator/ID Separation Protocol) Working Group";
  contact
    "lisp@ietf.org";
  description
    "This YANG module defines the generic configuration
     and operational data for LISP. The module can be extended by
     vendors to define vendor-specific LISP configuration
     parameters and policies.
     Copyright (c) 2014 IETF Trust and the persons identified as
     authors of the code.  All rights reserved.
     Redistribution and use in source and binary forms, with or
     without modification, is permitted pursuant to, and subject
     to the license terms contained in, the Simplified BSD License
     set forth in Section 4.c of the IETF Trust's Legal Provisions
     Relating to IETF Documents
     (http://trustee.ietf.org/license-info).
     This version of this YANG module is part of RFC 6338; see
     the RFC itself for full legal notices.
    ";
  revision 2016-06-30 {
    description
      "Initial revision.";
    reference
      "https://tools.ietf.org/html/rfc6830";
  }
  identity lisp-role {
    description
      "LISP router role.";
  }
  identity mapping-system {
    description
      "Mapping System interface";
  }
  identity single-node-mapping-system {
    base mapping-system;
    description
      "logically singular Map Server";
  }
  typedef mapping-system-ref {
    type identityref {
      base mapping-system;
    }
    description
      "Mapping System reference";
  }
  typedef lisp-role-ref {
    type identityref {
      base lisp-role;
    }
    description
      "LISP role reference";
  }
  typedef map-reply-action {
    type enumeration {
      enum no-action {
        value 0;
        description
          "Mapping is kept alive and no encapsulation occurs.";
      }
      enum natively-forward {
        value 1;
        description
          "Matching packets are not encapsulated or dropped but
           natively forwarded.";
      }
      enum send-map-request {
        value 2;
        description
          "Matching packets invoke Map-Requests.";
      }
      enum drop {
        value 3;
        description
          "Matching packets are dropped.";
      }
    }
    description
      "Defines the lisp map-cache ACT type";
    reference "https://tools.ietf.org/html/rfc6830#section-6.1.4";
  }
  typedef eid-id {
    type string;
    description
      "Type encoding of lisp-addresses to be generally used in EID
       keyed lists.";
  }
  typedef auth-key-type {
    type enumeration {
      enum none {
        value 0;
        description
          "No authentication.";
      }
      enum hmac-sha-1-96 {
        value 1;
        description
          "HMAC-SHA-1-96 (RFC2404) authentication is used.";
      }
      enum hmac-sha-256-128 {
        value 2;
        description
          "HMAC-SHA-256-128 (RFC4868) authentication is used.";
      }
    }
    description
      "Enumeration of the authentication mechansms supported by
       LISP.";
    reference
      "https://tools.ietf.org/html/rfc6830#section-6.1.6";
  }
  grouping locator-properties {
    description
      "Properties of a RLOC";
    leaf priority {
      type uint8;
      description
        "Locator priority.";
    }
    leaf weight {
      type uint8;
      description
        "Locator weight.";
    }
    leaf multicast-priority {
      type uint8;
      description
        "Locator's multicast priority";
    }
    leaf multicast-weight {
      type uint8;
      description
        "Locator's multicast weight";
    }
  }
  grouping locators-grouping {
    description
      "Group that defines a list of LISP locators.";
    // vina: container?
      list locator {
        key "id";
        description
          "List of routing locators";
        leaf id {
          type string {
            length "1..64";
          }
          description
            "Locator id";
        }
        container locator-address {
          uses lcaf:lisp-address;
          description
            "The locator address provided in LISP canonincal
             address format.";
        }
        uses locator-properties;
      }
  }
  grouping local-locators-grouping {
    description
      "Group that defines a list of LISP locators.";
    list interface {
      key "interface-ref";
      description
        "The address type of the locator";
      leaf interface-ref {
        type if:interface-ref;
        description
          "The name of the interface supporting the locator.";
      }
      uses locator-properties;
    }
  }
  grouping servicing-eids-grouping {
    description
      "Group of EIDs serviced by the this lisp device.";
    container servicing-eids {
      description
        "This node defines list of EIDs serviced by the this"
        + " lisp device.";
      list servicing-eid {
        key "id";
        description
          "List of EIDs serviced by the this lisp device.";
        leaf id {
          type lisp:eid-id;
          description
            "Id of serviced EID.";
        }
        container eid-address {
          uses lcaf:lisp-address;
          description
            "Serviced EID address in generic LISP address format.";
        }
      }
    }
  }
  grouping mappings {
    description
      "Group that defines a list of LISP mappings.";
    list mapping {
      key "id";
      description
        "List of EID to RLOCs mappings.";
      leaf id {
        type eid-id;
        description
          "Id that uniquely identifies a mapping.";
      }
      container eid {
        uses lcaf:lisp-address;
        description
          "End-host Identifier (EID) to be mapped to a list of
           locators";
      }
      leaf ttl {
        type uint32;
        description
          "Mapping validity period.";
      }
      leaf authoritative {
        type bits {
          bit A {
            description
              "Authoritative bit.";
          }
        }
        description
          "Bit that indicates if mapping comes from an
           authoritative source.";
      }
      leaf static {
        type boolean;
        default "false";
        description
          "This leaf should be true if the mapping is static.";
      }
      choice locator-list {
        description
          "list of locartors are either negative, or positive.";
        case negative-mapping {
          leaf map-reply-action {
            type map-reply-action;
            description
              "Forwarding action for a negative mapping.";
          }
        }
        case positive-mapping {
          container rlocs {
            uses locators-grouping;
            description
              "List of locators for a positive mapping.";
          }
        }
      }
    }
  }
  /* Configuration Data */
  container lisp {
    description
      "Configuration parameters for LISP subsystem.";
    container locator-sets {
      description
        "Container that defines a named locator set which can be
        referenced elsewhere.";
      list locator-set {
        key "locator-set-name";
        description
          "Multiple locator sets can be configured.";
        leaf locator-set-name {
          type string {
            length "1..64";
          }
          description
            "Locator set name";
        }
        choice locator-type {
          description
            "Locator sets can be based on local interfaces, or
             general locators.";
          case local-interface {
            uses local-locators-grouping;
            description
              "List of locators in this set based on local
              interfaces.";
          }
          case general-locator {
            uses locators-grouping;
            description
              "List of locators in this set based on lisp-address.";
          }
        }
      }
    }
    container lisp-router-instances {
      description
        "Configuration of LISP router instances.";
      list lisp-router-instance {
        key "lisp-router-instance-id";
        description
          "Each entry contains configuration of a lisp-router
           instance.";
        leaf lisp-router-instance-id {
          type int32;
          description
            "Arbitrary lisp-router id.";
        }
        list lisp-role {
          key lisp-role-type;
          description
            "List of lisp device roles such as MS, MR, ITR,
            ETR, RTR.";
          leaf lisp-role-type {
            type lisp-role-ref;
            description
              "The type of LISP device - identity derived from the
               'lisp-device' base identity.";
          }
          leaf enabled {
            type boolean;
            default "true";
            description
              "Enable/disable the lisp-role.";
          }
        }
      }
    }
  }
  /* Operational state data */
  container lisp-state {
    config false;
    description
      "Operational state of the LISP subsystem.";
    container lisp-router-instances {
      description
        "Configuration of LISP router instances.";
      list lisp-router-instance {
        key "lisp-router-instance-id";
        description
          "Each entry contains configuration of a lisp-router
          instance.";
        leaf lisp-router-instance-id {
          type int32;
          description
            "Arbitrary lisp-router id.";
        }
        list lisp-role {
          key lisp-role-type;
          description
            "List of lisp device roles such as MS, MR, ITR,
            ETR, RTR.";
          leaf lisp-role-type {
            type lisp-role-ref;
            description
              "The type of LISP device - identity derived from the
               'lisp-device' base identity.";
          }
          leaf enabled {
            type boolean;
            default "true";
            description
              "Enable/disable the lisp-role.";
          }
        }
      }
    }
  }
}
