module ietf-i2nsf-consumer-facing-interface {
  namespace
    "urn:ietf:params:xml:ns:yang:ietf-i2nsf-consumer-facing-interface";
  prefix
    capability-interface;
  import ietf-yang-types {
    prefix yang;
  }
    organization
    "IETF I2NSF (Interface to Network Security Functions)
     Working Group";
  contact
    "WG Web: <http://tools.ietf.org/wg/i2nsf>
     WG List: <mailto:i2nsf@ietf.org>
     WG Chair: Adrian Farrel
     <mailto:Adrain@olddog.co.uk>
     WG Chair: Linda Dunbar
     <mailto:Linda.duhbar@huawei.com>
     Editor: Jaehoon Paul Jeong
     <mailto:pauljeong@skku.edu>";
  description
    "This module defines a YANG data module for consumer-facing
     interface to security controller.";
  revision "2016-11-13"{
    description "Initial revision";
    reference
      "draft-kumar-i2nsf-client-facing-interface-im-01";
  }
  //Groupings
  grouping policy {
    description
      "policy is a grouping including a set of security rules
      according to certain logic, i.e., their similarity or mutual
      relations, etc. The network security policy is able
      to apply over both the unidirectional and bidirectional
      traffic across the NSF.";
    list policy-lifecycle {
      key "policy-lifecycle-id";
      description
        "The ID of the policy lifecycle for each policy.
        This must be unique.";
      leaf policy-lifecycle-id {
        type uint16;
        mandatory true;
        description
          "This is policy lifecycle-id.";
      }
      container expiration-event {
        description
          "The event which makes the policy expired.";
        leaf enabled {
          type boolean;
          mandatory true;
          description
            "This represents whether the policy is enabled or
            disabled.";
        }
        leaf event-id {
          type uint16;
          mandatory true;
          description
            "The ID of the event. This must be unique.";
        }
        leaf event-date {
          type yang:date-and-time;
          mandatory true;
          description
            "The date when the event is triggered.";
        }
      }
      container expiration-time {
        description
          "The time when the policy is expired.";
        leaf enabled {
          type boolean;
          mandatory true;
          description
            "This represents whether the policy is enabled or
            disabled.";
        }
        leaf time {
          type yang:date-and-time;
          mandatory true;
          description
            "The time when the policy is enabled.";
        }
      }
    }
    list policy-rule {
      key "policy-rule-id";
      description
        "The ID of the policy rule.
       This is key for policy-rule-list.
       This must be unique.";
      leaf policy-name {
        type string;
        mandatory true;
        description
          "The name of the policy.
       This must be unique.";
      }
      leaf policy-rule-id {
        type uint16;
        mandatory true;
        description
          "The ID of the policy rule. This must be unique.";
      }
      leaf policy-rule-date {
          type yang:date-and-time;
          mandatory true;
          description
            "The date when the date-and-time when the policy is
             created.";
        }
      container service {
        description
          "The services which NSFs could perform to manage the
          security attacks.
          This consists of voip-handling and volte-handling.
          This will be extended in later version.";
        leaf voip-handling {
          type boolean;
          mandatory true;
          description
            "This field represents whether the policy contains
            handling the voip packet flow.";
        }
        leaf volte-handling {
          type boolean;
          mandatory true;
          description
            "This field represents whether the policy contains
            handling the volte packet flow.";
        }
      }
      list condition {
        key "condition-id";
        description
          "The ID of the condition. This must be unique.";
        leaf condition-id {
        type uint16;
        mandatory true;
        description
          "This is condition id";
      }
        container caller {
          description
            "The caller of VoIP-VoLTE call";
          leaf caller-id {
            type uint16;
            mandatory true;
            description
              "The ID of the caller. This must be unique.";
          }
          container caller-location {
            description
              "The location of the caller.";
            leaf country {
              type string;
              mandatory true;
              description
                "The country of the caller.";
            }
            leaf city {
              type string;
              mandatory true;
              description
                "The city of the caller.";
            }
          }
        }
        container callee {
          description
            "The callee of VoIP-VoLTE call.";
          leaf callee-id {
            type uint16;
            mandatory true;
            description
              "The ID of the callee. This must be unique.";
          }
          container callee-location {
            description
              "The location of the callee.";
            leaf country {
              type string;
              mandatory true;
              description
                "The country of the callee.";
            }
            leaf city {
              type string;
              mandatory true;
              description
                "The city of the callee.";
            }
          }
        }
        container valid-time-interval {
          description
            "The time when the policy starts or ends to be valid.";
          leaf start-time {
            type yang:date-and-time;
            mandatory true;
            description
              "The time when the policy starts to be valid.";
          }
          leaf end-time {
            type yang:date-and-time;
            mandatory true;
            description
              "The time when the policy ends to be valid.";
          }
        }
      }
    }
    container action {
      description
        "TBD";
      choice action-type {
        description
          "The flow-based NSFs realize the network security
           functions by executing various Actions, which at least
           includes ingress-action, egress-action, and
           advanced-action.";
        case ingress-action {
          description
            "The ingress actions consist of permit, mirror and log.";
          leaf permit {
            type boolean;
            mandatory true;
            description
              "Packet flow is permitted or denyed.";
          }
          leaf mirror {
            type boolean;
            mandatory true;
            description
              "Packet flow is mirroried.";
          }
          leaf log {
            type boolean;
            mandatory true;
            description
              "Packet flow is logged.";
          }
        }
        case engress-type {
          description
            "The egress action consists of redirection. TBD";
          leaf redirection {
            type boolean;
            mandatory true;
            description
              "Packet flow is redireted.";
          }
        }
    container update {
        description
          "The event which makes the policy expired.";
        leaf update-id {
          type uint16;
            mandatory true;
            description
              "The policy update-id to distingush each update.
               This must be unique.";
          }
        leaf update-event-id {
          type uint16;
          mandatory true;
          description
            "The ID of the event. This must be unique.";
          }
          leaf update-enabled {
              type boolean;
              mandatory true;
              description
                "The update is enabled or disabled.";
            }
          leaf update-event-date {
            type yang:date-and-time;
            mandatory true;
            description
              "The date when the update-event is triggered.";
          }
          leaf update-log {
            type boolean;
            mandatory true;
            description
              "To log update and its description";
          }
        }
      }
    }
  }
}
