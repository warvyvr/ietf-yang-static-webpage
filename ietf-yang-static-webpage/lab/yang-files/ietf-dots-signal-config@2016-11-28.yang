module ietf-dots-signal-config {
     namespace "urn:ietf:params:xml:ns:yang:ietf-dots-signal-config";
     prefix "config";
     organization "Cisco Systems, Inc.";
     contact "Tirumaleswar Reddy <tireddy@cisco.com>";

     description
       "This module contains YANG definition for DOTS
       signal channel session configuration";

     revision 2016-11-28 {
       reference
       "https://tools.ietf.org/html/draft-reddy-dots-signal-channel";
     }

     container signal-config {
          description "top level container for DOTS signal channel session
                       configuration";
          leaf session-id {
              type int32;
              description "Identifier for the DOTS signal channel
                           session configuration data";
          }
          leaf heartbeat-timeout {
              type int16;
              description "heartbeat timeout";
          }
          leaf max-retransmit {
              type int16;
              description "Maximum number of retransmissions";
          }
          leaf ack-timeout {
              type int16;
              description "Initial retransmission timeout value";
          }
          leaf ack-random-factor {
              type decimal64 {
              fraction-digits 2;
              }
              description "Random factor used to influence the timing of
                           retransmissions";
         }
      }
}
