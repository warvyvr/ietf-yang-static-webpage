module ietf-sfc-oam {
    namespace "urn:ietf:params:xml:ns:yang:ietf-sfc-oam";
    prefix sfc-oam;

    import ietf-network{
      prefix nd;
    }

        import ietf-connectionless-oam{
         prefix "coam";
        }

        import ietf-connectionless-oam-methods{
         prefix "coam-methods";
        }

        import service-function-chain{
         prefix "sfc-sfc";
        }
        import sfc-common{
         prefix sfc-common;
        }

     import service-function  {
       prefix sfc-sf;
     }

     import service-function-forwarder  {
       prefix sfc-sff;
     }

         import service-function-path{
           prefix sfc-sfp;
         }

    organization "IETF SFC Working Group";

    contact

        "Gu Rong ";

    description
      "The YANG module defines a SFC OAM configuration model.";

    revision 2016-11-21 {
      description
        "Initial vision. - 00 version";
      reference "";
    }

/*service function oam blocks*/

   /*test point ipv4 extension*/

        /*oam type extension*/

    augment "/nd:networks/nd:network/nd:node/coam:location-type"
        +"/coam:ipv4-location-type/coam:test-point-ipv4-location-list"
        +"/coam:test-point-locations/coam:technology/coam:technology-string"{
         leaf sfc-oam{
          type string;
          description
          "sfc oam type";
         }
         description
         "augment the connectionless oam model to derive service
         functon oam yang model";
        }

        /*service function*/

        augment "/nd:networks/nd:network/nd:node/coam:location-type"
        +"/coam:ipv4-location-type/coam:test-point-ipv4-location-list"
        +"/coam:test-point-locations"{
         leaf sf-name {
          type leafref{
           path "/sfc-sf:service-functions/sfc-sf:service-function"
           +"/sfc-sf:name";
          }
      description
        "The name of the service function.";
         }

         leaf sf-type{
      type sfc-common:sft-type-name;

          description
          "The type of the service function";
         }
         leaf sfc-name {
          type leafref{
           path "/sfc-sfc:service-function-chains"
           +"/sfc-sfc:service-function-chain/sfc-sfc:name";
          }
          description
          "service function chain name";
         }
         leaf sfp-name {
          type leafref{
           path "/sfc-sfp:service-function-paths"
           +"/sfc-sfp:service-function-path/sfc-sfp:name";
          }
          description
          "Service function path name";
         }
         list sf-data-plane-locator {
          key "locator-name";
          leaf locator-name{
           type leafref{
            path "/sfc-sf:service-functions/sfc-sf:service-function"
            +"/sfc-sf:sf-data-plane-locator/sfc-sf:name";
          }
          description
          "The sf data plane locator name";
          }

         leaf service-function-forwarder{
          type sfc-common:sff-name;
          description
          "The name of teh service function forwarder";
         }

          description
          "list for service function data plane locator";
         }
         description
         "augment connectionless oam model to derive service
         function oam yang model";
        }

  /*test point ipv6 extension*/

   /*oam type extension*/

    augment "/nd:networks/nd:network/nd:node/coam:location-type"
        +"/coam:ipv6-location-type/coam:test-point-ipv6-location-list"
        +"/coam:test-point-locations/coam:technology/coam:technology-string"{
         leaf sfc-oam{
          type string;
          description
          "sfc oam type";
         }
         description
         "augment the connectionless oam model to derive service
         functon oam yang model";
        }

   /*service function*/

        augment "/nd:networks/nd:network/nd:node/coam:location-type"
        +"/coam:ipv6-location-type/coam:test-point-ipv6-location-list"
        +"/coam:test-point-locations"{
         leaf sf-name {
          type leafref{
           path "/sfc-sf:service-functions/sfc-sf:service-function"
           +"/sfc-sf:name";
          }
      description
        "The name of the service function.";
         }
         leaf sf-type{
      type sfc-common:sft-type-name;
          description
          "The type of the service function";
         }
         leaf sfc-name {
          type leafref{
           path "/sfc-sfc:service-function-chains"
           +"/sfc-sfc:service-function-chain/sfc-sfc:name";
          }
          description
          "service function chain name";
         }
         leaf sfp-name {
          type leafref{
           path "/sfc-sfp:service-function-paths"
           +"/sfc-sfp:service-function-path/sfc-sfp:name";
          }
          description
          "Service function path name";

         }

         leaf classifier{
          type leafref{
           path "/sfc-sfp:service-function-paths"
           +"/sfc-sfp:service-function-path/sfc-sfp:classifier";
          }
                  description
                  "SFC classifier.";
         }
         list sf-data-plane-locator {
          key "locator-name";
          leaf locator-name{
           type leafref{
            path "/sfc-sf:service-functions/sfc-sf:service-function"
            +"/sfc-sf:sf-data-plane-locator/sfc-sf:name";
          }
          description
          "The sf data plane locator name";
          }
          leaf service-function-forwarder{
          type leafref{
           path "/sfc-sff:service-function-forwarders"
           +"/sfc-sff:service-function-forwarder/sfc-sff:name";
          }
          description
          "The name of teh service function forwarder";
         }
          description
          "List for service function data plane locator";
         }
         description
         "augment connectionless oam model to derive service
         function oam yang model";
        }

        augment "/coam-methods:continuity-check/coam-methods:input"
        +"/coam-methods:destination-tp/coam-methods:tp-address"{
         case sfc-address{

         leaf sf-name {
          type leafref{
           path "/sfc-sf:service-functions/sfc-sf:service-function"
           +"/sfc-sf:name";
          }
         description
         "The name of the service function.";
         }

         leaf sfc-name {

          type leafref{

           path "/sfc-sfc:service-function-chains"
           +"/sfc-sfc:service-function-chain/sfc-sfc:name";
          }
          description
          "service function chain name";
         }

         leaf sfp-name {
          type leafref{
           path "/sfc-sfp:service-function-paths"
           +"/sfc-sfp:service-function-path/sfc-sfp:name";
          }
          description
          "Service function path name";
         }

         leaf classifier{
          type leafref{
           path "/sfc-sfp:service-function-paths"
           +"/sfc-sfp:service-function-path/sfc-sfp:classifier";
          }
                  description
                  "SFC classifier";
         }
          leaf service-function-forwarder{
          type leafref{
           path "/sfc-sff:service-function-forwarders"
           +"/sfc-sff:service-function-forwarder/sfc-sff:name";
           }
                   description
                   "service function forwarder";
          }
          description
          "SFC address";
         }
                 description
                 "Augment base with SFC address";
        }

        augment "/coam-methods:path-discovery/coam-methods:input"
        +"/coam-methods:destination-tp/coam-methods:tp-address"{
         case sfc-address{

         leaf sf-name {
          type leafref{
           path "/sfc-sf:service-functions/sfc-sf:service-function"

           +"/sfc-sf:name";
          }
      description
        "The name of the service function.";
         }

         leaf sfc-name {
          type leafref{

           path "/sfc-sfc:service-function-chains"
           +"/sfc-sfc:service-function-chain/sfc-sfc:name";
          }
          description
          "service function chain name";
         }

         leaf sfp-name {
          type leafref{
           path "/sfc-sfp:service-function-paths"
           +"/sfc-sfp:service-function-path/sfc-sfp:name";
          }
          description
          "Service function path name";
         }

         leaf classifier{
          type leafref{
           path "/sfc-sfp:service-function-paths"
           +"/sfc-sfp:service-function-path/sfc-sfp:classifier";
          }
                  description
                  "SFC classifier";
         }
          leaf service-function-forwarder{
          type leafref{
           path "/sfc-sff:service-function-forwarders"
           +"/sfc-sff:service-function-forwarder/sfc-sff:name";
           }
                   description
                   "Service function forwarder";
          }
          description
          "SFC address";
         }
                 description
                 "Augment base model with SFC address";
        }
}
