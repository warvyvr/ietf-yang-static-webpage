module example-newco-acl {

  yang-version 1.1;

  namespace "urn:newco:params:xml:ns:yang:example-newco-acl";

  prefix example-newco-acl;

  import ietf-access-control-list {
    prefix "ietf-acl";
  }

  import ietf-interfaces {
    prefix "ietf-if";
  }

  import ietf-yang-types {
    prefix yang;
  }

  organization
    "Newco model group.";

  contact
    "abc@newco.com";
  description
    "This YANG module augment IETF ACL Yang.";

  revision 2016-10-12{
    description
      "Creating NewCo proprietary extensions to ietf-acl model";
    reference
      "RFC XXXX: Network Access Control List (ACL)
      YANG Data  Model";
  }

  typedef known-ether-type {
    type enumeration {
      enum "ipv4" {
        value 2048; // 0x0800
        description "Internet Protocol version 4 (IPv4)";
      }
      enum "vlan-tagged" {
        value 33024; // 0x8100
        description "VLAN-tagged frame (IEEE 802.1Q) & Shortest Path Bridging IEEE 802.1aq[4]";
      }
      enum "ipv6" {

        value 34525; // 0x86DD
        description "Internet Protocol Version 6 (IPv6)";
      }
      enum "mpls-unicast" {
        value 34887; // 0x8847
        description "MPLS unicast";
      }
      enum "mpls-multicast" {
        value 34888; // 0x8848
        description "MPLS multicast";
      }
    }
    description "Listing supported Ethertypes";
  }

  typedef ipv4-flags-type {
     type bits {
        bit ipv4-reserved {
         position 0;
         description "reserved bit";
        }
        bit ipv4-DF {
         position 1;
         description "DF bit";
        }
        bit ipv4-MF {
         position 2;
         description "MF bit";
        }
     }
     description "IPv4 flag types";
  }

  augment "/ietf-acl:access-lists/ietf-acl:acl/ietf-acl:access-list-entries/ietf-acl:ace/ietf-acl:matches" {
   when "ietf-acl:access-lists/ietf-acl:acl/ietf-acl:acl-type = 'ace-eth'";

   description "additional MAC header matching";

     leaf vlan-tagged {
       type uint16;
       description "Ethernet frame with VLAN tag";
     }

     leaf mpls-unicast {
       type uint16;
       description "Ethernet frame with MPLS unicast payload";
     }

     leaf mpls-multicast {
       type uint16;
       description "Ethernet frame with MPLS multicast payload";
     }

     leaf ipv4 {
       type uint16;
       description "Ethernet frame with IPv4 unicast payload";
     }

     leaf ipv6 {
       type uint16;
       description "Ethernet frame with IPv4 unicast payload";
     }
  }
  augment "/ietf-acl:access-lists/ietf-acl:acl/ietf-acl:access-list-entries/ietf-acl:ace/ietf-acl:matches" {
   when "ietf-acl:access-lists/ietf-acl:acl/ietf-acl:acl-type = 'ipv4-acl'";

   description "additional IP header information";

    leaf ipv4-ttl {
      type uint8;
      description "time to live of a given packet as defined in RFC791";
    }

    leaf ipv4-len {
      type uint16;
      description "total packet length as defined in RFC791";
    }

    leaf ipv4-ihl {
      type uint8 {
         range 0..15;
      }
      description "Internet Header Length in 32 bit words (see RFC791).  Note
                   that while the minimum value for this field in a packet is
                   5, we leave open the possibility here that the packet has
                   been corrupted.";
    }

    leaf ipv4-id {
      type uint16;
      description "Identification as decribed in RFC791";
    }

    leaf ipv4-flags {
      type ipv4-flags-type;
      description "IPv4 flags as defined in RFC791";

    }

    leaf ipv4-offset {
      type uint16 {
         range 0..8191;
      }
      description "Matches on the packet fragment offset";
    }
   }

   augment "/ietf-acl:access-lists/ietf-acl:acl/ietf-acl:access-list-entries/ietf-acl:ace/ietf-acl:matches" {
    description "Newco proprietary simple filter matches";
    choice protocol-payload-choice {
      description "Newo proprietary payload match condition";
      list protocol-payload {
        key value-keyword;
        ordered-by user;
        description "Match protocol payload";
        uses match-simple-payload-protocol-value;
      }
    }

    choice metadata {
      description "Newco proprietary interface match condition";
      list interface-name {
        key input-interface;
        ordered-by user;
        description "Match interface name";
        uses metadata;
      }
    }
  }

  augment "/ietf-acl:access-lists/ietf-acl:acl/ietf-acl:access-list-entries/ietf-acl:ace/ietf-acl:actions" {
    description "Newco proprietary simple filter actions";
    choice action {
      description "";
      case count {
        description "Count the packet in the named counter";
        leaf count {
          type string;
          description "";
        }
      }
      case policer {
        description "Name of policer to use to rate-limit traffic";
        leaf policer {
          type string;

          description "";
        }
      }
      case hiearchical-policer {
        description "Name of hierarchical policer to use to
        rate-limit traffic";
        leaf hierarchitacl-policer{
          type string;
          description "";
        }
      }
    }
  }

  augment "/ietf-acl:access-lists/ietf-acl:acl" {
    description "Newco proprietary default action";
    container default-actions {
      description
        "Actions that occur if no access-list entry is matched.";
      leaf deny {
        type empty;
        description "";
      }
    }
  }

  grouping metadata {
    description
    "Fields associated with a packet which are not in
    the header.";
    leaf input-interface {
      type ietf-if:interface-ref {
        require-instance false;
      }
      description
        "Packet was received on this interface";
    }
  }

  grouping match-simple-payload-protocol-value {
    description "Newco proprietary payload";
    leaf value-keyword {
      type enumeration {
        enum icmp {
          description "Internet Control Message Protocol";
        }
        enum icmp6 {
          description "Internet Control Message Protocol Version 6";

        }
        enum range {
          description "Range of values";
        }
      }

      description "(null)";
    }
  }

  augment "/ietf-if:interfaces/ietf-if:interface" {
    description "Apply ACL to interfaces";
    container acl{
      description "ACL related properties.";
      leaf acl-name {
        type ietf-acl:access-control-list-ref;
        description "Access Control List name.";
      }
      leaf match-counter {
        type yang:counter64;
        config false;
        description
          "Total match count for Access Control
          List on this interface";
      }
      choice direction {
        description "Applying ACL in which traffic direction";
        leaf in {
          type empty;
          description "Inbound traffic";
        }
        leaf out {
          type empty;
          description "Outbound traffic";
        }
      }
    }
  }

  augment "/ietf-acl:access-lists/ietf-acl:acl/ietf-acl:acl-oper-data" {
    description
      "This is an example on how to apply acl to a target to collect
      operational data";
    container targets{
      description "To which object is the ACL attached to";
      choice interface{
        description "Access Control List was attached to this interface";
        leaf-list interface-name{

          type ietf-if:interface-ref {
            require-instance true;
          }
        description "Attached to this interface name";
        }
      }
    }
  }
}
