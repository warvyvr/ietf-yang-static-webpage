module ietf-pcep {
    yang-version 1.1;
    namespace "urn:ietf:params:xml:ns:yang:ietf-pcep";
    prefix pcep;
    import ietf-inet-types {
        prefix "inet";
    }
    import ietf-yang-types {
        prefix "yang";
    }
    import ietf-te {
        prefix "te";
    }
    import ietf-te-types {
       prefix "te-types";
    }
    import ietf-key-chain {
       prefix "key-chain";
    }
    import ietf-netconf-acm {
       prefix nacm;
     }
    organization
        "IETF PCE (Path Computation Element) Working Group";
    contact
        "WG Web:   <http://tools.ietf.org/wg/pce/>
         WG List:  <mailto:pce@ietf.org>
         WG Chair: JP Vasseur
                   <mailto:jpv@cisco.com>
         WG Chair: Julien Meuric
                   <mailto:julien.meuric@orange.com>
         WG Chair: Jonathan Hardwick
                   <mailto:Jonathan.Hardwick@metaswitch.com>
         Editor:   Dhruv Dhody
                   <mailto:dhruv.ietf@gmail.com>";
    description
        "The YANG module defines a generic configuration and
         operational model for PCEP common across all of the
         vendor implementations.";
    revision 2017-03-12 {
        description "Initial revision.";
        reference
            "RFC XXXX:  A YANG Data Model for Path Computation
                        Element Communications Protocol
                        (PCEP)";
    }
    /*
     * Identities
     */
    identity pcep {
        description "Identity for the PCEP protocol.";
    }
    /*
     * Typedefs
     */
    typedef pcep-role {
        type enumeration {
            enum unknown {
                value "0";
                description
                "An unknown role";
            }
            enum pcc {
                value "1";
                description
                "The role of a Path Computation Client";
            }
            enum pce {
                value "2";
                description
                "The role of Path Computation Element";
            }
            enum pcc-and-pce {
                value "3";
                description
                "The role of both Path Computation Client and
                 Path Computation Element";
            }
        }
        description
            "The role of a PCEP speaker.
             Takes one of the following values
             - unknown(0): the role is not known.
             - pcc(1): the role is of a Path Computation
               Client (PCC).
             - pce(2): the role is of a Path Computation
               Server (PCE).
             - pccAndPce(3): the role is of both a PCC and
               a PCE.";
    }
    typedef pcep-admin-status {
        type enumeration {
                enum admin-status-up {
                value "1";
                description
                "Admin Status is Up";
            }
            enum admin-status-down {
                value "2";
                description
                "Admin Status is Down";
            }
        }
        description
        "The Admin Status of the PCEP entity.
         Takes one of the following values
             - admin-status-up(1): Admin Status is Up.
             - admin-status-down(2): Admin Status is Down";
    }
    typedef pcep-oper-status {
        type enumeration {
            enum oper-status-up {
                value "1";
                description
                "The PCEP entity is active";
            }
            enum oper-status-down {
                value "2";
                description
                "The PCEP entity is inactive";
            }
            enum oper-status-going-up {
                value "3";
                description
                "The PCEP entity is activating";
            }
            enum oper-status-going-down {
                value "4";
                description
                "The PCEP entity is deactivating";
            }
            enum oper-status-failed {
                value "5";
                description
                "The PCEP entity has failed and will recover
                 when possible.";
            }
            enum oper-status-failed-perm {
                value "6";
                description
                "The PCEP entity has failed and will not recover
                 without operator intervention";
            }
        }
        description
        "The operational status of the PCEP entity.
         Takes one of the following values
             - oper-status-up(1): Active
             - oper-status-down(2): Inactive
             - oper-status-going-up(3): Activating
             - oper-status-going-down(4): Deactivating
             - oper-status-failed(5): Failed
             - oper-status-failed-perm(6): Failed Permanantly";
    }
    typedef pcep-initiator {
        type enumeration {
            enum local {
                value "1";
                description
                "The local PCEP entity initiated the session";
            }
            enum remote {
                value "2";
                description
                "The remote PCEP peer initiated the session";
            }
        }
        description
        "The initiator of the session, that is, whether the TCP
         connection was initiated by the local PCEP entity or
         the remote peer.
         Takes one of the following values
             - local(1): Initiated locally
             - remote(2): Initiated remotely";
    }
    typedef pcep-sess-state {
        type enumeration {
            enum tcp-pending {
                value "1";
                description
                    "The tcp-pending state of PCEP session.";
            }
            enum open-wait {
                value "2";
                description
                    "The open-wait state of PCEP session.";
            }
            enum keep-wait {
                value "3";
                description
                    "The keep-wait state of PCEP session.";
            }
            enum session-up {
                value "4";
                description
                    "The session-up state of PCEP session.";
            }
        }
        description
            "The current state of the session.
             The set of possible states excludes the idle state
             since entries do not exist in the idle state.
             Takes one of the following values
                - tcp-pending(1): PCEP TCP Pending state
                - open-wait(2): PCEP Open Wait state
                - keep-wait(3): PCEP Keep Wait state
                - session-up(4): PCEP Session Up state";
    }
    typedef domain-type {
        type enumeration {
            enum ospf-area {
                value "1";
                description
                    "The OSPF area.";
            }
            enum isis-area {
                value "2";
                description
                    "The IS-IS area.";
            }
            enum as {
                value "3";
                description
                    "The Autonomous System (AS).";
            }
        }
        description
            "The PCE Domain Type";
    }
    typedef domain-ospf-area {
        type union {
            type uint32;
            type yang:dotted-quad;
       }
       description
            "OSPF Area ID.";
    }
    typedef domain-isis-area {
        type string {
            pattern '[0-9A-Fa-f]{2}\.([0-9A-Fa-f]{4}\.){0,3}';
        }
        description
            "IS-IS Area ID.";
    }
    typedef domain-as {
        type uint32;
        description
            "Autonomous System number.";
    }
    typedef domain {
        type union {
            type domain-ospf-area;
            type domain-isis-area;
            type domain-as;
        }
        description
            "The Domain Information";
    }
    typedef operational-state {
        type enumeration {
            enum down {
                value "0";
                description
                    "not active.";
            }
            enum up {
                value "1";
                description
                    "signalled.";
            }
            enum active {
                value "2";
                description
                    "up and carrying traffic.";
            }
            enum going-down {
                value "3";
                description
                    "LSP is being torn down, resources are
                     being released.";
            }
            enum going-up {
                value "4";
                description
                    "LSP is being signalled.";
            }
        }
        description
            "The operational status of the LSP";
    }
    typedef lsp-error {
        type enumeration {
            enum no-error {
                value "0";
                description
                    "No error, LSP is fine.";
            }
            enum unknown {
                value "1";
                description
                    "Unknown reason.";
            }
            enum limit {
                value "2";
                description
                    "Limit reached for PCE-controlled LSPs.";
            }
            enum pending {
                value "3";
                description
                    "Too many pending LSP update requests.";
            }
            enum unacceptable {
                value "4";
                description
                    "Unacceptable parameters.";
            }
            enum internal {
                value "5";
                description
                    "Internal error.";
            }
            enum admin {
                value "6";
                description
                    "LSP administratively brought down.";
            }
            enum preempted {
                value "7";
                description
                    "LSP preempted.";
            }
            enum rsvp {
                value "8";
                description
                    "RSVP signaling error.";
            }
        }
        description
            "The LSP Error Codes.";
    }
    typedef sync-state {
        type enumeration {
            enum pending {
                value "0";
                description
                    "The state synchronization
                     has not started.";
            }
            enum ongoing {
                value "1";
                description
                    "The state synchronization
                     is ongoing.";
            }
            enum finished {
                value "2";
                description
                    "The state synchronization
                     is finished.";
            }
        }
        description
            "The LSP-DB state synchronization operational
            status.";
    }
    typedef pst{
        type enumeration{
            enum rsvp-te{
                value "0";
                description
                    "RSVP-TE signaling protocol";
            }
            enum sr{
                value "1";
                description
                    "Segment Routing Traffic Engineering";
            }
        }
        description
            "The Path Setup Type";
    }
    typedef assoc-type{
        type enumeration{
            enum protection{
                value "1";
                description
                    "Path Protection Association Type";
            }
            enum policy{
                value "2";
                description
                    "Policy Association Type";
            }
            enum diversity{
                value "3";
                description
                    "Diversity Association Type";
            }
        }
        description
            "The PCEP Association Type";
    }
    typedef objective-function{
        type enumeration{
            enum mcp{
                value "1";
                description
                    "Minimum Cost Path (MCP)";
            }
            enum mlp{
                value "2";
                description
                    "Minimum Load Path (MLP)";
            }
            enum mbp{
                value "3";
                description
                    "Maximum residual Bandwidth Path (MBP)";
            }
            enum mbc{
                value "4";
                description
                    "Minimize aggregate Bandwidth Consumption
                     (MBC)";
            }
            enum mll{
                value "5";
                description
                    "Minimize the Load of the most loaded Link
                     (MLL)";
            }
            enum mcc{
                value "6";
                description
                    "Minimize the Cumulative Cost of a set of
                    paths (MCC)";
            }
            enum spt{
                value "7";
                description
                    "Shortest Path Tree (SPT)";
            }
            enum mct{
                value "8";
                description
                    "Minimum Cost Tree (MCT)";
            }
            enum mplp{
                value "9";
                description
                    "Minimum Packet Loss Path (MPLP)";
            }
            enum mup{
                value "10";
                description
                    "Maximum Under-Utilized Path (MUP)";
            }
            enum mrup{
                value "11";
                description
                    "Maximum Reserved Under-Utilized Path
                     (MRUP)";
            }
        }
        description
            "The PCEP Objective functions";
    }
    /*
     * Features
     */
    feature svec {
        description
            "Support synchronized path computation.";
    }
    feature gmpls {
        description
            "Support GMPLS.";
    }
    feature objective-function {
        description
            "Support OF as per RFC 5541.";
    }
    feature gco {
        description
            "Support GCO as per RFC 5557.";
    }
    feature path-key {
        description
            "Support path-key as per RFC 5520.";
    }
    feature p2mp {
        description
            "Support P2MP as per RFC 6006.";
    }
    feature stateful {
        description
            "Support stateful PCE.";
    }
    feature stateful-sync-opt {
        description
            "Support stateful sync optimization";
    }
    feature pce-initiated {
        description
            "Support PCE-Initiated LSP.";
    }
    feature tls {
        description
            "Support PCEP over TLS.";
    }
    feature sr {
        description
            "Support Segment Routing for PCE.";
    }
    /*
     * Groupings
     */
    grouping pcep-entity-info{
        description
            "This grouping defines the attributes for PCEP entity.";
        leaf connect-timer {
            type uint32 {
                range "1..65535";
            }
            units "seconds";
            default 60;
            description
                "The time in seconds that the PCEP entity will wait
                 to establish a TCP connection with a peer.  If a
                 TCP connection is not established within this time
                 then PCEP aborts the session setup attempt.";
            reference
                "RFC 5440: Path Computation Element (PCE)
                           Communication Protocol (PCEP)";
        }
        leaf connect-max-retry {
            type uint32;
            default 5;
            description
                "The maximum number of times the system tries to
                 establish a TCP connection to a peer before the
                 session with the peer transitions to the idle
                 state.";
            reference
                "RFC 5440: Path Computation Element (PCE)
                           Communication Protocol (PCEP)";
        }
        leaf init-backoff-timer {
            type uint32 {
                range "1..65535";
            }
            units "seconds";
            description
               "The initial back-off time in seconds for retrying
                a failed session setup attempt to a peer.
                The back-off time increases for each failed
                session setup attempt, until a maximum back-off
                time is reached.  The maximum back-off time is
                max-backoff-timer.";
        }
        leaf max-backoff-timer {
            type uint32;
            units "seconds";
            description
               "The maximum back-off time in seconds for retrying
                a failed session setup attempt to a peer.
                The back-off time increases for each failed session
                setup attempt, until this maximum value is reached.
                Session setup attempts then repeat periodically
                without any further increase in back-off time.";
        }
        leaf open-wait-timer {
            type uint32 {
                range "1..65535";
            }
            units "seconds";
            default 60;
            description
               "The time in seconds that the PCEP entity will wait
                to receive an Open message from a peer after the
                TCP connection has come up.
                If no Open message is received within this time then
                PCEP terminates the TCP connection and deletes the
                associated sessions.";
            reference
                "RFC 5440: Path Computation Element (PCE)
                           Communication Protocol (PCEP)";
        }
        leaf keep-wait-timer {
            type uint32 {
                range "1..65535";
            }
            units "seconds";
            default 60;
            description
                "The time in seconds that the PCEP entity will wait
                 to receive a Keepalive or PCErr message from a peer
                 during session initialization after receiving an
                 Open message.  If no Keepalive or PCErr message is
                 received within this time then PCEP terminates the
                 TCP connection and deletes the associated
                 sessions.";
            reference
                "RFC 5440: Path Computation Element (PCE)
                           Communication Protocol (PCEP)";
        }
        leaf keep-alive-timer {
            type uint32 {
                range "0..255";
            }
            units "seconds";
            default 30;
            description
                "The keep alive transmission timer that this PCEP
                 entity will propose in the initial OPEN message of
                 each session it is involved in.  This is the
                 maximum time between two consecutive messages sent
                 to a peer. Zero means that the PCEP entity prefers
                 not to send Keepalives at all.
                 Note that the actual Keepalive transmission
                 intervals, in either direction of an active PCEP
                 session, are determined by negotiation between the
                 peers as specified by RFC 5440, and so may differ
                 from this configured value.";
            reference
                "RFC 5440: Path Computation Element (PCE)
                           Communication Protocol (PCEP)";
        }
        leaf dead-timer {
            type uint32 {
                range "0..255";
            }
            units "seconds";
            must "(. > ../keep-alive-timer)" {
                error-message "The dead timer must be "
                       + "larger than the keep alive timer";
                description
                    "This value MUST be greater than
                     keep-alive-timer.";
            }
            default 120;
            description
                "The dead timer that this PCEP entity will propose
                 in the initial OPEN message of each session it is
                 involved in. This is the time after which a peer
                 should declare a session down if it does not
                 receive any PCEP messages. Zero suggests that the
                 peer does not run a dead timer at all." ;
            reference
                "RFC 5440: Path Computation Element (PCE)
                           Communication Protocol (PCEP)";
        }
        leaf allow-negotiation{
            type boolean;
            description
                "Whether the PCEP entity will permit negotiation of
                 session parameters.";
        }
        leaf max-keep-alive-timer{
            type uint32 {
                range "0..255";
            }
            units "seconds";
            description
                "In PCEP session parameter negotiation in seconds,
                 the maximum value that this PCEP entity will
                 accept from a peer for the interval between
                 Keepalive transmissions. Zero means that the PCEP
                 entity will allow no Keepalive transmission at
                 all." ;
        }
        leaf max-dead-timer{
            type uint32 {
                range "0..255";
            }
            units "seconds";
            description
                "In PCEP session parameter negotiation in seconds,
                 the maximum value that this PCEP entity will accept
                 from a peer for the Dead timer.  Zero means that
                 the PCEP entity will allow not running a Dead
                 timer.";
        }
        leaf min-keep-alive-timer{
            type uint32 {
                range "0..255";
            }
            units "seconds";
            description
                "In PCEP session parameter negotiation in seconds,
                 the minimum value that this PCEP entity will
                 accept for the interval between Keepalive
                 transmissions. Zero means that the PCEP entity
                 insists on no Keepalive transmission at all.";
        }
        leaf min-dead-timer{
            type uint32 {
                range "0..255";
            }
            units "seconds";
            description
                 "In PCEP session parameter negotiation in
                  seconds, the minimum value that this PCEP entity
                  will accept for the Dead timer.  Zero means that
                  the PCEP entity insists on not running a Dead
                  timer.";
        }
        leaf sync-timer{
            if-feature svec;
            type uint32 {
                range "0..65535";
            }
            units "seconds";
            default 60;
            description
                "The value of SyncTimer in seconds is used in the
                 case of synchronized path computation request
                 using the SVEC object. Consider the case where a
                 PCReq message is received by a PCE that contains
                 the SVEC object referring to M synchronized path
                 computation requests.  If after the expiration of
                 the SyncTimer all the M path computation requests
                 have not been, received a protocol error is
                 triggered and the PCE MUST cancel the whole set
                 of path computation requests.
                 The aim of the SyncTimer is to avoid the storage
                 of unused synchronized requests should one of
                 them get lost for some reasons (for example, a
                 misbehaving PCC).
                 Zero means that the PCEP entity does not use the
                 SyncTimer.";
            reference
                "RFC 5440: Path Computation Element (PCE)
                           Communication Protocol (PCEP)";
        }
        leaf request-timer{
            type uint32 {
                range "1..65535";
            }
            units "seconds";
            description
                "The maximum time that the PCEP entity will wait
                 for a response to a PCReq message.";
        }
        leaf max-sessions{
            type uint32;
            description
               "Maximum number of sessions involving this PCEP
                entity that can exist at any time.";
        }
        leaf max-unknown-reqs{
            type uint32;
            default 5;
            description
              "The maximum number of unrecognized requests and
               replies that any session on this PCEP entity is
               willing to accept per minute before terminating
               the session.
               A PCRep message contains an unrecognized reply
               if it contains an RP object whose request ID
               does not correspond to any in-progress request
               sent by this PCEP entity.
               A PCReq message contains an unrecognized request
               if it contains an RP object whose request ID is
               zero.";
            reference
                "RFC 5440: Path Computation Element (PCE)
                           Communication Protocol (PCEP)";
        }
        leaf max-unknown-msgs{
            type uint32;
            default 5;
            description
             "The maximum number of unknown messages that any
              session on this PCEP entity is willing to accept
              per minute before terminating the session.";
            reference
                "RFC 5440: Path Computation Element (PCE)
                           Communication Protocol (PCEP)";
        }
    }//pcep-entity-info
    grouping pce-scope{
        description
            "This grouping defines PCE path computation scope
             information which maybe relevant to PCE selection.
             This information corresponds to PCE auto-discovery
             information.";
        reference
            "RFC 5088: OSPF Protocol Extensions for Path
                       Computation Element (PCE)
                       Discovery
             RFC 5089: IS-IS Protocol Extensions for Path
                       Computation Element (PCE)
                       Discovery";
        leaf intra-area-scope{
            type boolean;
            default true;
            description
                "PCE can compute intra-area paths.";
        }
        leaf intra-area-pref{
            type uint8{
                range "0..7";
            }
            description
              "The PCE's preference for intra-area TE LSP
              computation.";
        }
        leaf inter-area-scope{
            type boolean;
            default false;
            description
                "PCE can compute inter-area paths.";
        }
        leaf inter-area-scope-default{
            type boolean;
            default false;
            description
                "PCE can act as a default PCE for inter-area
                 path computation.";
        }
        leaf inter-area-pref{
            type uint8{
                range "0..7";
            }
            description
              "The PCE's preference for inter-area TE LSP
              computation.";
        }
        leaf inter-as-scope{
            type boolean;
            default false;
            description
                "PCE can compute inter-AS paths.";
        }
        leaf inter-as-scope-default{
            type boolean;
            default false;
            description
                "PCE can act as a default PCE for inter-AS
                 path computation.";
        }
        leaf inter-as-pref{
            type uint8{
                range "0..7";
            }
            description
              "The PCE's preference for inter-AS TE LSP
              computation.";
        }
        leaf inter-layer-scope{
            type boolean;
            default false;
            description
                "PCE can compute inter-layer paths.";
        }
        leaf inter-layer-pref{
            type uint8{
                range "0..7";
            }
            description
              "The PCE's preference for inter-layer TE LSP
              computation.";
        }
    }//pce-scope
    grouping domain{
        description
            "This grouping specifies a Domain where the
             PCEP speaker has topology visibility.";
        leaf domain-type{
            type domain-type;
            description
              "The domain type.";
        }
        leaf domain{
            type domain;
            description
              "The domain Information.";
        }
    }//domain
    grouping capability{
        description
            "This grouping specifies a capability
             information of local PCEP entity. This maybe
             relevant to PCE selection as well. This
             information corresponds to PCE auto-discovery
             information.";
        reference
            "RFC 5088: OSPF Protocol Extensions for Path
                       Computation Element (PCE)
                       Discovery
             RFC 5089: IS-IS Protocol Extensions for Path
                       Computation Element (PCE)
                       Discovery";
        leaf gmpls{
            if-feature gmpls;
            type boolean;
            description
              "Path computation with GMPLS link
               constraints.";
        }
        leaf bi-dir{
            type boolean;
            description
              "Bidirectional path computation.";
        }
        leaf diverse{
            type boolean;
            description
              "Diverse path computation.";
        }
        leaf load-balance{
            type boolean;
            description
              "Load-balanced path computation.";
        }
        leaf synchronize{
            if-feature svec;
            type boolean;
            description
              "Synchronized paths computation.";
        }
        leaf objective-function{
            if-feature objective-function;
            type boolean;
            description
              "Support for multiple objective functions.";
        }
        leaf add-path-constraint{
            type boolean;
            description
              "Support for additive path constraints (max
               hop count, etc.).";
        }
        leaf prioritization{
            type boolean;
            description
              "Support for request prioritization.";
        }
        leaf multi-request{
            type boolean;
            description
              "Support for multiple requests per message.";
        }
        leaf gco{
            if-feature gco;
            type boolean;
            description
              "Support for Global Concurrent Optimization
               (GCO).";
        }
        leaf p2mp{
            if-feature p2mp;
            type boolean;
            description
              "Support for P2MP path computation.";
        }
        container stateful{
            if-feature stateful;
            description
                "If stateful PCE feature is present";
            leaf enabled{
                type boolean;
                description
                    "Enabled or Disabled";
            }
            leaf active{
                type boolean;
                description
                  "Support for active stateful PCE.";
            }
            leaf pce-initiated{
                if-feature pce-initiated;
                type boolean;
                description
                  "Support for PCE-initiated LSP.";
            }
            leaf include-db-ver{
                if-feature stateful-sync-opt;
                type boolean;
                description
                    "Support inclusion of LSP-DB-VERSION
                    in LSP object";
            }
            leaf trigger-resync{
                if-feature stateful-sync-opt;
                type boolean;
                description
                    "Support PCE triggered re-synchronization";
            }
            leaf trigger-initial-sync{
                if-feature stateful-sync-opt;
                type boolean;
                description
                    "PCE triggered initial synchronization";
            }
            leaf incremental-sync{
                if-feature stateful-sync-opt;
                type boolean;
                description
                    "Support incremental (delta) sync";
            }
        }
        container sr{
            if-feature sr;
            description
                "If segment routing is supported";
            leaf enabled{
                type boolean;
                description
                    "Enabled or Disabled";
            }
        }
    }//capability
    grouping info{
        description
            "This grouping specifies all information which
             maybe relevant to both PCC and PCE.
             This information corresponds to PCE auto-discovery
             information.";
        container domain{
            description
                "The local domain for the PCEP entity";
            list domain{
                key "domain-type domain";
                description
                    "The local domain.";
                uses domain{
                    description
                        "The local domain for the PCEP entity.";
                }
            }
        }
        container capability{
            description
                "The PCEP entity capability";
            uses capability{
                description
                    "The PCEP entity supported
                    capabilities.";
            }
        }
    }//info
    grouping pce-info{
        description
            "This grouping specifies all PCE information
             which maybe relevant to the PCE selection.
             This information corresponds to PCE auto-discovery
             information.";
        container scope{
            description
                "The path computation scope";
            uses pce-scope;
        }
        container neigh-domains{
            description
                "The list of neighbour PCE-Domain
                 toward which a PCE can compute
                 paths";
            list domain{
                key "domain-type domain";
                description
                    "The neighbour domain.";
                uses domain{
                    description
                        "The PCE neighbour domain.";
                }
            }
        }
    }//pce-info
    grouping lsp-state{
        description
            "This grouping defines the attributes for LSP in LSP-DB.
             These are the attributes specifically from the PCEP
             perspective";
        leaf plsp-id{
            type uint32{
                range "1..1048575";
            }
            description
                "A PCEP-specific identifier for the LSP.  A PCC
                 creates a unique PLSP-ID for each LSP that is
                 constant for the lifetime of a PCEP session.
                 PLSP-ID is 20 bits with 0 and 0xFFFFF are
                 reserved";
        }
        leaf pcc-id{
            type inet:ip-address;
            description
                "The local internet address of the PCC, that
                 generated the PLSP-ID.";
        }
        container lsp-ref{
            description
                "reference to ietf-te lsp state";
            leaf source {
                type leafref {
                    path "/te:te/te:lsps-state/te:lsp/te:source";
                }
                description
                  "Tunnel sender address extracted from
                  SENDER_TEMPLATE  object";
                reference "RFC3209";
            }
            leaf destination {
                type leafref {
                    path "/te:te/te:lsps-state/te:lsp/te:"
                         + "destination";
                }
                description
                    "Tunnel endpoint address extracted from
                    SESSION object";
                reference "RFC3209";
            }
            leaf tunnel-id {
                type leafref {
                    path "/te:te/te:lsps-state/te:lsp/te:tunnel-id";
                }
                description
                    "Tunnel identifier used in the SESSION
                    that remains constant over the life
                    of the tunnel.";
                reference "RFC3209";
            }
            leaf lsp-id {
                type leafref {
                    path "/te:te/te:lsps-state/te:lsp/te:lsp-id";
                }
                description
                    "Identifier used in the SENDER_TEMPLATE
                    and the FILTER_SPEC that can be changed
                    to allow a sender to share resources with
                    itself.";
                reference "RFC3209";
            }
            leaf extended-tunnel-id {
                type leafref {
                    path "/te:te/te:lsps-state/te:lsp/te:"
                    + "extended-tunnel-id";
                }
                description
                    "Extended Tunnel ID of the LSP.";
                reference "RFC3209";
            }
            leaf type {
                type leafref {
                    path "/te:te/te:lsps-state/te:lsp/te:type";
                }
                description "LSP type P2P or P2MP";
            }
        }
        leaf admin-state{
            type boolean;
            description
                "The desired operational state";
        }
        leaf operational-state{
            type operational-state;
            description
                "The operational status of the LSP";
        }
        container delegated{
            description
                "The delegation related parameters";
            leaf enabled{
                type boolean;
                description
                    "LSP is delegated or not";
            }
            leaf peer{
                type leafref {
                    path "/pcep-state/entity/peers/peer/addr";
                }
                must "(../enabled = true())"
                {
                    error-message
                        "The LSP must be delegated";
                    description
                        "When LSP is a delegated LSP";
                }
                description
                    "At the PCC, the reference to the PCEP peer to
                    which LSP is delegated; At the PCE, the
                    reference to the PCEP peer which delegated this
                    LSP";
            }
            leaf srp-id{
                type uint32;
                description
                    "The last SRP-ID-number associated with this
                    LSP.";
            }
        }
        container initiation {
            if-feature pce-initiated;
            description
                "The PCE initiation related parameters";
            leaf enabled{
                type boolean;
                description
                    "LSP is PCE-initiated or not";
            }
            leaf peer{
                type leafref {
                    path "/pcep-state/entity/peers/peer/addr";
                }
                must "(../enabled = true())"
                {
                    error-message
                        "The LSP must be PCE-Initiated";
                    description
                        "When the LSP must be PCE-Initiated";
                }
                description
                    "At the PCC, the reference to the PCEP peer
                    that initiated this LSP; At the PCE, the
                    reference to the PCEP peer where the LSP
                    is initiated";
            }
        }
        leaf symbolic-path-name{
            type string;
            description
                "The symbolic path name associated with the LSP.";
        }
        leaf last-error{
            type lsp-error;
            description
                "The last error for the LSP.";
        }
        leaf pst{
            type pst;
            default "rsvp-te";
            description
                "The Path Setup Type";
        }
    }//lsp-state
    grouping notification-instance-hdr {
        description
            "This group describes common instance specific data
             for notifications.";
        leaf peer-addr {
            type leafref {
                path "/pcep-state/entity/peers/peer/addr";
            }
            description
                "Reference to peer address";
        }
    }// notification-instance-hdr
    grouping notification-session-hdr {
        description
        "This group describes common session instance specific
         data for notifications.";
        leaf session-initiator {
            type leafref {
            path "/pcep-state/entity/peers/peer/sessions/" +
                 "session/initiator";
            }
            description
                "Reference to pcep session initiator leaf";
        }
    }// notification-session-hdr
    grouping stateful-pce-parameter {
        description
        "This group describes stateful PCE specific
         parameters.";
        leaf state-timeout{
            type uint32;
            units "seconds";
            description
                "When a PCEP session is terminated, a PCC
                 waits for this time period before flushing
                 LSP state associated with that PCEP session
                 and reverting to operator-defined default
                 parameters or behaviours.";
        }
        leaf redelegation-timeout{
            when "../../role = 'pcc'" +
                 "or " +
                 "../../role = 'pcc-and-pce'"
            {
                description
                    "Valid at PCC";
            }
            type uint32;
            units "seconds";
            description
                "When a PCEP session is terminated, a PCC
                 waits for this time period before revoking
                 LSP delegation to a PCE and attempting to
                 redelegate LSPs associated with the
                 terminated PCEP session to an alternate
                 PCE.";
        }
        leaf rpt-non-pcep-lsp{
            when "../../role = 'pcc'" +
                 "or " +
                 "../../role = 'pcc-and-pce'"
            {
                description
                    "Valid at PCC";
            }
            type boolean;
            default true;
            description
                "If set, a PCC reports LSPs that are not
                controlled by any PCE (for example, LSPs
                that are statically configured at the
                PCC). ";
        }
    }
    grouping authentication {
        description "Authentication Information";
        choice auth-type-selection {
            description
                "Options for expressing authentication setting.";
            case auth-key-chain {
                leaf key-chain {
                    type key-chain:key-chain-ref;
                    description
                        "key-chain name.";
                }
            }
            case auth-key {
               leaf crypto-algorithm {
                 type identityref {
                   base key-chain:crypto-algorithm;
                 }
                 mandatory true;
                 description
                   "Cryptographic algorithm associated with key.";
               }
               container key-string {
                 description
                   "The key string.";
                 nacm:default-deny-all;
                 choice key-string-style {
                   description
                     "Key string styles";
                   case keystring {
                     leaf keystring {
                       type string;
                       description
                         "Key string in ASCII format.";
                     }
                   }
                   case hexadecimal {
                     if-feature "key-chain:hex-key-string";
                     leaf hexadecimal-string {
                       type yang:hex-string;
                       description
                         "Key in hexadecimal string format. When
                          compared to ASCII, specification in
                          hexadecimal affords greater key
                          entropy with the same number of
                          octets. Additionally, it discourages
                          usage of well-known words or
                          numbers.";
                     }
                   }
                 }
               }
            }
            case auth-tls {
                if-feature tls;
                container tls {
                    description
                        "TLS related information - TBD";
                }
            }
        }
    }
    grouping path-key {
        description "Path-key related information";
        leaf enabled{
            type boolean;
            description
                "Enabled or Disabled";
        }
        leaf discard-timer {
            type uint32;
            units "minutes";
            default 10;
            description
                "A timer to discard unwanted path-keys";
        }
        leaf reuse-time {
            type uint32;
            units "minutes";
            default 30;
            description
                "A time after which the path-keys could be reused";
        }
        leaf pce-id {
            type inet:ip-address;
            description
                "PCE Address to be used in each Path-Key Subobject
                (PKS)";
        }
    }
    grouping path-key-state {
        description "Table to allow inspection of path-keys";
        list path-keys{
            key "path-key";
            description
                "The list of path-keys generated by the PCE";
            leaf path-key {
                type uint16;
                description
                    "The identifier, or token used to represent
                     the Confidential Path Segment (CPS) within
                     the context of the PCE";
            }
            container cps {
                description
                    "The Confidential Path Segment (CPS)";
                list explicit-route-objects {
                    key "index";
                    description
                        "List of explicit route objects";
                    leaf explicit-route-usage {
                        type identityref {
                            base te-types:route-usage-type;
                        }
                        description
                            "An explicit-route hop action.";
                    }
                    uses te-types:explicit-route-hop_config;
                }
            }
            leaf pcc-original {
                type leafref {
                    path "/pcep-state/entity/peers/peer/addr";
                }
                description
                    "Reference to PCC peer address of
                    the original request";
            }
            leaf req-id {
                type uint32;
                description
                    "The request ID of the original PCReq.";
            }
            leaf retrieved  {
                type boolean;
                description
                    "If path-key has been retrieved yet";
            }
            leaf pcc-retrieved {
                type leafref {
                    path "/pcep-state/entity/peers/peer/addr";
                }
                must "(../retrieved = true())"
                {
                    error-message
                        "The Path-key should be retreived";
                    description
                        "When Path-Key has been retreived";
                }
                description
                    "Reference to PCC peer address which
                    retreived the path-key";
            }
            leaf creation-time {
                type yang:timestamp;
                description
                    "The timestamp value at the time this Path-Key
                    was created.";
            }
            leaf discard-time {
                type uint32;
                units "minutes";
                description
                    "A time after which this path-keys will be
                    discarded";
            }
            leaf reuse-time {
                type uint32;
                units "minutes";
                description
                    "A time after which this path-keys could be
                    reused";
            }
        }
    }
    grouping of-list {
        description "List of OF";
        list objective-function{
            key "of";
            description
                "The list of authorized OF";
            leaf of {
                type objective-function;
                description
                    "The OF authorized";
            }
        }
    }
    grouping association {
        description
            "Generic Association parameters";
        leaf type {
            type "assoc-type";
            description
                "The PCEP association type";
        }
        leaf id {
            type uint16;
            description
                "PCEP Association ID";
        }
        leaf source {
          type inet:ip-address;
          description
                "PCEP Association Source.";
        }
        leaf global-source {
          type uint32;
          description
                "PCEP Association Global
                Source.";
        }
        leaf extended-id{
            type string;
            description
                "Additional information to
                support unique identification.";
        }
    }
    grouping association-ref {
        description
            "Generic Association parameters";
        leaf id {
            type leafref {
                path "/pcep-state/entity/lsp-db/"
                + "association-list/id";
            }
            description
                "PCEP Association ID";
        }
        leaf source {
            type leafref {
                path "/pcep-state/entity/lsp-db/"
                + "association-list/source";
            }
          description
                "PCEP Association Source.";
        }
        leaf global-source {
            type leafref {
                path "/pcep-state/entity/lsp-db/"
                + "association-list/global-source";
            }
          description
                "PCEP Association Global
                Source.";
        }
        leaf extended-id{
            type leafref {
                path "/pcep-state/entity/lsp-db/"
                + "association-list/extended-id";
            }
            description
                "Additional information to
                support unique identification.";
        }
    }
    /*
     * Configuration data nodes
     */
    container pcep{
        presence
            "The PCEP is enabled";
            description
            "Parameters for list of configured PCEP entities
             on the device.";
        container entity {
            description
                "The configured PCEP entity on the device.";
            leaf addr {
                type inet:ip-address;
                mandatory true;
                description
                    "The local Internet address of this PCEP
                    entity.
                    If operating as a PCE server, the PCEP
                    entity listens on this address.
                    If operating as a PCC, the PCEP entity
                    binds outgoing TCP connections to this
                    address.
                    It is possible for the PCEP entity to
                    operate both as a PCC and a PCE Server, in
                    which case it uses this address both to
                    listen for incoming TCP connections and to
                    bind outgoing TCP connections.";
            }
            leaf enabled {
                type boolean;
                default true;
                description
                    "The administrative status of this PCEP
                     Entity.";
            }
            leaf role {
                type pcep-role;
                mandatory true;
                description
                    "The role that this entity can play.
                     Takes one of the following values.
                     - unknown(0): this PCEP Entity role is not
                       known.
                     - pcc(1): this PCEP Entity is a PCC.
                     - pce(2): this PCEP Entity is a PCE.
                     - pcc-and-pce(3): this PCEP Entity is both
                       a PCC and a PCE.";
            }
            leaf description {
                type string;
                description
                    "Description of the PCEP entity configured
                     by the user";
            }
            leaf speaker-entity-id{
                if-feature stateful-sync-opt;
                type string;
                description
                    "The Speaker Entity Identifier";
            }
            uses info {
                description
                    "Local PCEP entity information";
            }
            container pce-info {
                when "../role = 'pce'" +
                     "or " +
                     "../role = 'pcc-and-pce'"
                {
                    description
                        "Valid at PCE";
                }
                uses pce-info {
                    description
                        "Local PCE information";
                }
                container path-key {
                    if-feature path-key;
                    uses path-key {
                        description
                            "Path-Key Configuration";
                    }
                    description
                        "Path-Key Configuration";
                }
                description
                    "The Local PCE Entity PCE information";
            }
            uses authentication {
                description
                    "Local PCEP entity authentication information";
            }
            uses pcep-entity-info {
                description
                    "The configuration related to the PCEP
                     entity.";
            }
            leaf pcep-notification-max-rate {
                type uint32;
                mandatory true;
                description
                    "This variable indicates the maximum number of
                     notifications issued per second. If events
                     occur more rapidly, the implementation may
                     simply fail to emit these notifications during
                     that period, or may queue them until an
                     appropriate time. A value of 0 means no
                     notifications are emitted and all should be
                     discarded (that is, not queued).";
            }
            container stateful-parameter{
                if-feature stateful;
                must "(/pcep/entity/capability/stateful/enabled" +
                     " = true())"
                {
                    error-message
                        "The Stateful PCE must be enabled";
                    description
                        "When PCEP entity is stateful
                         enabled";
                }
                uses stateful-pce-parameter;
                description
                    "The configured stateful parameters";
            }
            container of-list{
                when "../role = 'pce'" +
                     "or " +
                     "../role = 'pcc-and-pce'"
                {
                    description
                        "Valid at PCE";
                }
                if-feature objective-function;
                uses of-list;
                description
                    "The authorized OF-List at PCE for all peers";
            }
            container peers{
                when "../role = 'pcc'" +
                     "or " +
                     "../role = 'pcc-and-pce'"
                {
                    description
                        "Valid at PCC";
                }
                description
                    "The list of configured peers for the
                     entity (remote PCE)";
                list peer{
                    key "addr";
                    description
                        "The peer configured for the entity.
                         (remote PCE)";
                    leaf addr {
                        type inet:ip-address;
                        description
                            "The local Internet address of this
                             PCEP peer.";
                    }
                    leaf description {
                        type string;
                        description
                            "Description of the PCEP peer
                             configured by the user";
                    }
                    uses info {
                        description
                            "PCE Peer information";
                    }
                    uses pce-info {
                        description
                            "PCE Peer information";
                    }
                    leaf delegation-pref{
                        if-feature stateful;
                        type uint8{
                            range "0..7";
                        }
                        must "(/pcep/entity/capability/stateful" +
                             "/active = true())"
                        {
                            error-message
                                "The Active Stateful PCE must be
                                 enabled";
                            description
                                "When PCEP entity is active stateful
                                 enabled";
                        }
                        description
                            "The PCE peer delegation preference.";
                    }
                    uses authentication {
                        description
                            "PCE Peer authentication";
                    }
                }//peer
            }//peers
        }//entity
    }//pcep
    /*
     * Operational data nodes
     */
    container pcep-state{
        config false;
        description
            "The list of operational PCEP entities on the
             device.";
        container entity{
            description
                "The operational PCEP entity on the device.";
            leaf addr {
                type inet:ip-address;
                description
                    "The local Internet address of this PCEP
                    entity.
                    If operating as a PCE server, the PCEP
                    entity listens on this address.
                    If operating as a PCC, the PCEP entity
                    binds outgoing TCP connections to this
                    address.
                    It is possible for the PCEP entity to
                    operate both as a PCC and a PCE Server, in
                    which case it uses this address both to
                    listen for incoming TCP connections and to
                    bind outgoing TCP connections.";
            }
            leaf index{
                type uint32;
                description
                    "The index of the operational PECP
                     entity";
            }
            leaf admin-status {
                type pcep-admin-status;
                description
                    "The administrative status of this PCEP Entity.
                     This is the desired operational status as
                     currently set by an operator or by default in
                     the implementation.  The value of enabled
                     represents the current status of an attempt
                     to reach this desired status.";
            }
            leaf oper-status {
                type pcep-admin-status;
                description
                   "The operational status of the PCEP entity.
                    Takes one of the following values.
                    - oper-status-up(1): the PCEP entity is
                      active.
                    - oper-status-down(2): the PCEP entity is
                      inactive.
                    - oper-status-going-up(3): the PCEP entity is
                      activating.
                    - oper-status-going-down(4): the PCEP entity is
                      deactivating.
                    - oper-status-failed(5): the PCEP entity has
                      failed and will recover when possible.
                    - oper-status-failed-perm(6): the PCEP entity
                      has failed and will not recover without
                      operator intervention.";
            }
            leaf role {
                type pcep-role;
                description
                    "The role that this entity can play.
                     Takes one of the following values.
                     - unknown(0): this PCEP entity role is
                       not known.
                     - pcc(1): this PCEP entity is a PCC.
                     - pce(2): this PCEP entity is a PCE.
                     - pcc-and-pce(3): this PCEP entity is
                       both a PCC and a PCE.";
            }
            leaf description {
                type string;
                description
                    "Description of the PCEP entity configured
                     by the user";
            }
            leaf speaker-entity-id{
                if-feature stateful-sync-opt;
                type string;
                description
                    "The Speaker Entity Identifier";
            }
            uses info {
                description
                    "Local PCEP entity information";
            }
            container pce-info {
                when "../role = 'pce'" +
                     "or " +
                     "../role = 'pcc-and-pce'"
                {
                    description
                        "Valid at PCE";
                }
                uses pce-info {
                    description
                        "Local PCE information";
                }
                container path-key {
                    if-feature path-key;
                    uses path-key {
                        description
                            "Path-Key Configuration";
                    }
                    description
                        "Path-Key Configuration";
                }
                description
                    "The Local PCE Entity PCE information";
            }
            uses authentication {
                description
                    "Local PCEP Entity authentication information";
            }
            uses pcep-entity-info{
                description
                    "The operational information related to the
                     PCEP entity.";
            }
            container stateful-parameter{
                if-feature stateful;
                must "(/pcep/entity/capability/stateful/enabled" +
                     " = true())"
                {
                    error-message
                        "The Stateful PCE must be enabled";
                    description
                        "When PCEP entity is stateful
                         enabled";
                }
                uses stateful-pce-parameter;
                description
                    "The operational stateful parameters";
            }
            container lsp-db{
                if-feature stateful;
                description
                    "The LSP-DB";
                leaf db-ver{
                    when "../../role = 'pcc'" +
                         "or " +
                         "../../role = 'pcc-and-pce'"
                    {
                        description
                            "Valid at PCC";
                    }
                    if-feature stateful-sync-opt;
                    type uint64;
                    description
                        "The LSP State Database Version Number";
                }
                list association-list {
                    key "id source global-source extended-id";
                    description
                        "List of all PCEP associations";
                    uses association {
                        description
                            "The Association attributes";
                    }
                    list lsp {
                        key "plsp-id pcc-id";
                        description
                            "List of all LSP in this association";
                        leaf plsp-id {
                            type leafref {
                                path "/pcep-state/entity/lsp-db/"
                                + "lsp/plsp-id";
                            }
                            description
                                "Reference to PLSP-ID in LSP-DB";
                        }
                        leaf pcc-id {
                            type leafref {
                                path "/pcep-state/entity/lsp-db/"
                                + "lsp/pcc-id";
                            }
                            description
                                "Reference to PCC-ID in LSP-DB";
                        }
                    }
                }
                list lsp{
                    key "plsp-id pcc-id";
                    description
                        "List of all LSPs in LSP-DB";
                    uses lsp-state{
                        description
                            "The PCEP specific attributes for
                             LSP-DB.";
                    }
                    list association-list {
                        key "id source global-source extended-id";
                        description
                            "List of all PCEP associations";
                        uses association-ref {
                            description
                                "Reference to the Association
                                 attributes";
                        }
                    }
                }
            }
            container path-keys {
                when "../role = 'pce'" +
                     "or " +
                     "../role = 'pcc-and-pce'"
                {
                    description
                        "Valid at PCE";
                }
                if-feature path-key;
                uses path-key-state;
                description
                    "The path-keys generated by the PCE";
            }
            container of-list{
                when "../role = 'pce'" +
                     "or " +
                     "../role = 'pcc-and-pce'"
                {
                    description
                        "Valid at PCE";
                }
                if-feature objective-function;
                uses of-list;
                description
                    "The authorized OF-List at PCE for all peers";
            }
            container peers{
                description
                        "The list of peers for the entity";
                list peer{
                    key "addr";
                    description
                        "The peer for the entity.";
                    leaf addr {
                        type inet:ip-address;
                        description
                            "The local Internet address of this PCEP
                             peer.";
                    }
                    leaf role {
                        type pcep-role;
                        description
                            "The role of the PCEP Peer.
                             Takes one of the following values.
                             - unknown(0): this PCEP peer role
                               is not known.
                             - pcc(1): this PCEP peer is a PCC.
                             - pce(2): this PCEP peer is a PCE.
                             - pcc-and-pce(3): this PCEP peer
                               is both a PCC and a PCE.";
                    }
                    uses info {
                        description
                            "PCEP peer information";
                    }
                    container pce-info {
                        when "../role = 'pce'" +
                             "or " +
                             "../role = 'pcc-and-pce'"
                        {
                            description
                                "When the peer is PCE";
                        }
                        uses pce-info {
                            description
                                "PCE Peer information";
                        }
                    description
                        "The PCE Peer information";
                    }
                    leaf delegation-pref{
                        when "../role = 'pce'" +
                             "or " +
                             "../role = 'pcc-and-pce'"
                        {
                            description
                                "When the peer is PCE";
                        }
                        if-feature stateful;
                        type uint8{
                            range "0..7";
                        }
                        must "(/pcep/entity/capability/stateful" +
                             "/active = true())"
                        {
                            error-message
                                "The Active Stateful PCE must be
                                 enabled";
                            description
                                "When PCEP entity is active stateful
                                 enabled";
                        }
                        description
                            "The PCE peer delegation preference.";
                    }
                    uses authentication {
                        description
                            "PCE Peer authentication";
                    }
                    leaf discontinuity-time {
                        type yang:timestamp;
                        description
                            "The timestamp of the time when the
                             information and statistics were
                             last reset.";
                    }
                    leaf initiate-session {
                        type boolean;
                        description
                            "Indicates whether the local PCEP
                             entity initiates sessions to this peer,
                             or waits for the peer to initiate a
                             session.";
                    }
                    leaf session-exists{
                        type boolean;
                        description
                            "Indicates whether a session with
                             this peer currently exists.";
                    }
                    leaf session-up-time{
                        type yang:timestamp;
                        description
                           "The timestamp value of the last time a
                            session with this peer was successfully
                            established.";
                    }
                    leaf session-fail-time{
                        type yang:timestamp;
                        description
                          "The timestamp value of the last time a
                           session with this peer failed to be
                           established.";
                    }
                    leaf session-fail-up-time{
                        type yang:timestamp;
                        description
                          "The timestamp value of the last time a
                           session with this peer failed from
                           active.";
                    }
                    container sessions {
                        description
                            "This entry represents a single PCEP
                             session in which the local PCEP entity
                             participates.
                             This entry exists only if the
                             corresponding PCEP session has been
                             initialized by some event, such as
                             manual user configuration, auto-
                             discovery of a peer, or an incoming
                             TCP connection.";
                        list session {
                            key "initiator";
                            description
                                "The list of sessions, note that
                                 for a time being two sessions
                                 may exist for a peer";
                            leaf initiator {
                                type pcep-initiator;
                                description
                                    "The initiator of the session,
                                     that is, whether the TCP
                                     connection was initiated by
                                     the local PCEP entity or the
                                     peer.
                                     There is a window during
                                     session initialization where
                                     two sessions can exist between
                                     a pair of PCEP speakers, each
                                     initiated by one of the
                                     speakers. One of these
                                     sessions is always discarded
                                     before it leaves OpenWait
                                     state. However, before it is
                                     discarded, two sessions to the
                                     given peer appear transiently
                                     in this MIB module. The
                                     sessions are distinguished by
                                     who initiated them, and so this
                                     field is the key.";
                            }
                            leaf role {
                                type leafref {
                                    path "../../../role";
                                }
                                description
                                    "The reference to peer role .";
                            }
                            leaf state-last-change {
                                type yang:timestamp;
                                description
                                    "The timestamp value at the
                                     time this session entered its
                                     current state as denoted by
                                     the state leaf.";
                            }
                            leaf state {
                                type pcep-sess-state;
                                description
                                    "The current state of the
                                     session.
                                     The set of possible states
                                     excludes the idle state since
                                     entries do not exist in the
                                     idle state.";
                            }
                            leaf session-creation {
                                type yang:timestamp;
                                description
                                    "The timestamp value at the
                                     time this session was
                                     created.";
                            }
                            leaf connect-retry {
                                type yang:counter32;
                                description
                                     "The number of times that the
                                      local PCEP entity has
                                      attempted to establish a TCP
                                      connection for this session
                                      without success. The PCEP
                                      entity gives up when this
                                      reaches connect-max-retry.";
                            }
                            leaf local-id {
                                type uint32 {
                                  range "0..255";
                                }
                                description
                                     "The value of the PCEP session
                                      ID used by the local PCEP
                                      entity in the Open message
                                      for this session.
                                      If state is tcp-pending then
                                      this is the session ID that
                                      will be used in the Open
                                      message. Otherwise, this is
                                      the session ID that was sent
                                      in the Open message.";
                            }
                            leaf remote-id {
                                type uint32 {
                                    range "0..255";
                                }
                                must "((../state != 'tcp-pending'" +
                                     "and " +
                                     "../state != 'open-wait' )" +
                                     "or " +
                                     "((../state = 'tcp-pending'" +
                                     " or " +
                                     "../state = 'open-wait' )" +
                                     "and (. = 0)))" {
                                        error-message
                                            "Invalid remote-id";
                                        description
                                             "If state is tcp-
                                              pending or open-wait
                                              then this leaf is not
                                              used and MUST be set
                                              to zero.";
                                    }
                                description
                                     "The value of the PCEP session
                                      ID used by the peer in its
                                      Open message for this
                                      session.";
                            }
                            leaf keepalive-timer {
                                type uint32 {
                                  range "0..255";
                                }
                                units "seconds";
                                must "(../state = 'session-up'" +
                                     "or " +
                                     "(../state != 'session-up'" +
                                     "and (. = 0)))" {
                                        error-message
                                            "Invalid keepalive
                                             timer";
                                        description
                                            "This field is used if
                                             and only if state is
                                             session-up. Otherwise,
                                             it is not used and
                                             MUST be set to
                                             zero.";
                                    }
                                description
                                     "The agreed maximum interval at
                                      which the local PCEP entity
                                      transmits PCEP messages on
                                      this PCEP session.  Zero means
                                      that the local PCEP entity
                                      never sends Keepalives on this
                                      session.";
                            }
                            leaf peer-keepalive-timer {
                                type uint32 {
                                  range "0..255";
                                }
                                units "seconds";
                                must "(../state = 'session-up'" +
                                     "or "   +
                                     "(../state != 'session-up'" +
                                     "and " +
                                     "(. = 0)))" {
                                        error-message
                                            "Invalid Peer keepalive
                                             timer";
                                        description
                                            "This field is used if
                                             and only if state is
                                             session-up. Otherwise,
                                             it is not used and MUST
                                             be set to zero.";
                                    }
                                description
                                     "The agreed maximum interval at
                                      which the peer transmits PCEP
                                      messages on this PCEP session.
                                      Zero means that the peer never
                                      sends Keepalives on this
                                      session.";
                            }
                            leaf dead-timer {
                                type uint32 {
                                  range "0..255";
                                }
                                units "seconds";
                                description
                                     "The dead timer interval for
                                      this PCEP session.";
                            }
                            leaf peer-dead-timer {
                                type uint32 {
                                  range "0..255";
                                }
                                units "seconds";
                                must "((../state != 'tcp-pending'" +
                                     "and " +
                                     "../state != 'open-wait' )" +
                                     "or " +
                                     "((../state = 'tcp-pending'" +
                                     " or " +
                                     "../state = 'open-wait' )" +
                                     "and " +
                                     "(. = 0)))" {
                                        error-message
                                            "Invalid Peer Dead
                                             timer";
                                        description
                                            "If state is tcp-
                                             pending or open-wait
                                             then this leaf is not
                                             used and MUST be set to
                                             zero.";
                                    }
                                description
                                     "The peer's dead-timer interval
                                      for this PCEP session.";
                            }
                            leaf ka-hold-time-rem {
                                type uint32 {
                                  range "0..255";
                                }
                                units "seconds";
                                must "((../state != 'tcp-pending'" +
                                     "and " +
                                     "../state != 'open-wait' ) " +
                                     "or " +
                                     "((../state = 'tcp-pending'" +
                                     "or " +
                                     "../state = 'open-wait' )" +
                                     "and " +
                                     "(. = 0)))" {
                                        error-message
                                            "Invalid Keepalive hold
                                             time remaining";
                                        description
                                            "If state is tcp-pending
                                             or open-wait then this
                                             field is not used and
                                             MUST be set to zero.";
                                    }
                                description
                                     "The keep alive hold time
                                      remaining for this session.";
                            }
                            leaf overloaded {
                                type boolean;
                                description
                                     "If the local PCEP entity has
                                      informed the peer that it is
                                      currently overloaded, then
                                      this is set to true.
                                      Otherwise, it is set to
                                      false.";
                            }
                            leaf overload-time {
                                type uint32;
                                units "seconds";
                                must "((../overloaded = true()) " +
                                 "or ((../overloaded != true()) " +
                                 "and (. = 0)))" {
                                        error-message
                                            "Invalid overload-time";
                                        description
                                            "This field is only used
                                             if overloaded is set to
                                             true. Otherwise, it is
                                             not used and MUST be
                                             set to zero.";
                                    }
                                description
                                     "The interval of time that is
                                      remaining until the local PCEP
                                      entity will cease to be
                                      overloaded on this session.";
                            }
                            leaf peer-overloaded {
                                type boolean;
                                description
                                     "If the peer has informed the
                                      local PCEP entity that it is
                                      currently overloaded, then
                                      this is set to true.
                                      Otherwise, it is set to
                                      false.";
                            }
                            leaf peer-overload-time {
                                type uint32;
                                units "seconds";
                                must "((../peer-overloaded = " +
                                     "true()) or " +
                                     "((../peer-overloaded !=" +
                                     "true())" +
                                     " and " +
                                     "(. = 0)))" {
                                        error-message
                                            "Invalid peer overload
                                             time";
                                        description
                                            "This field is only used
                                             if peer-overloaded is
                                             set to true. Otherwise,
                                             it is not used and MUST
                                             be set to zero.";
                                    }
                                description
                                     "The interval of time that is
                                      remaining until the peer will
                                      cease to be overloaded.  If it
                                      is not known how long the peer
                                      will stay in overloaded state,
                                      this leaf is set to zero.";
                            }
                            leaf lspdb-sync {
                                if-feature stateful;
                                type sync-state;
                                description
                                    "The LSP-DB state
                                    synchronization status.";
                            }
                            leaf recv-db-ver{
                                when "../role = 'pcc'" +
                                     "or " +
                                     "../role = 'pcc-and-pce'"
                                {
                                    description
                                        "Valid for PCEP Peer as
                                        PCC";
                                }
                                if-feature stateful;
                                if-feature stateful-sync-opt;
                                type uint64;
                                description
                                    "The last received LSP State
                                    Database Version Number";
                            }
                            container of-list{
                                when "../role = 'pce'" +
                                     "or " +
                                     "../role = 'pcc-and-pce'"
                                {
                                    description
                                        "Valid for PCEP Peer as
                                        PCE";
                                }
                                if-feature objective-function;
                                uses of-list;
                                description
                                    "Indicate the list of supported
                                    OF on this session";
                            }
                            leaf speaker-entity-id{
                                if-feature stateful-sync-opt;
                                type string;
                                description
                                    "The Speaker Entity Identifier";
                            }
                            leaf discontinuity-time {
                                type yang:timestamp;
                                description
                                     "The timestamp value of the
                                      time when the statistics were
                                      last reset.";
                            }
                        } // session
                    } // sessions
                }//peer
            }//peers
        }//entity
    }//pcep-state
    /*
     * Notifications
     */
    notification pcep-session-up {
        description
            "This notification is sent when the value of
             '/pcep/pcep-state/peers/peer/sessions/session/state'
             enters the 'session-up' state.";
        uses notification-instance-hdr;
        uses notification-session-hdr;
        leaf state-last-change {
            type yang:timestamp;
            description
                "The timestamp value at the time this session
                entered its current state as denoted by the state
                leaf.";
        }
        leaf state {
            type pcep-sess-state;
            description
                "The current state of the session.
                 The set of possible states excludes the idle state
                 since entries do not exist in the idle state.";
        }
    } //notification
    notification pcep-session-down {
        description
            "This notification is sent when the value of
             '/pcep/pcep-state/peers/peer/sessions/session/state'
             leaves the 'session-up' state.";
        uses notification-instance-hdr;
        leaf session-initiator {
            type pcep-initiator;
            description
                "The initiator of the session.";
        }
        leaf state-last-change {
            type yang:timestamp;
            description
                "The timestamp value at the time this session
                entered its current state as denoted by the state
                leaf.";
        }
        leaf state {
            type pcep-sess-state;
            description
                "The current state of the session.
                 The set of possible states excludes the idle state
                 since entries do not exist in the idle state.";
        }
    } //notification
    notification pcep-session-local-overload {
        description
            "This notification is sent when the local PCEP entity
            enters overload state for a peer.";
        uses notification-instance-hdr;
        uses notification-session-hdr;
        leaf overloaded {
            type boolean;
            description
                 "If the local PCEP entity has informed the peer
                 that it is currently overloaded, then this is set
                 to true. Otherwise, it is set to false.";
        }
        leaf overload-time {
            type uint32;
            units "seconds";
            description
                 "The interval of time that is remaining until the
                 local PCEP entity will cease to be overloaded on
                 this session.";
        }
    } //notification
    notification pcep-session-local-overload-clear {
        description
            "This notification is sent when the local PCEP entity
            leaves overload state for a peer.";
        uses notification-instance-hdr;
        leaf overloaded {
            type boolean;
            description
                 "If the local PCEP entity has informed the peer
                 that it is currently overloaded, then this is set
                 to true.  Otherwise, it is set to false.";
        }
    } //notification
    notification pcep-session-peer-overload {
        description
            "This notification is sent when a peer enters overload
            state.";
        uses notification-instance-hdr;
        uses notification-session-hdr;
        leaf peer-overloaded {
            type boolean;
            description
                "If the peer has informed the local PCEP entity that
                it is currently overloaded, then this is set to
                true. Otherwise, it is set to false.";
        }
        leaf peer-overload-time {
            type uint32;
            units "seconds";
            description
                "The interval of time that is remaining until the
                peer will cease to be overloaded.  If it is not
                known how long the peer will stay in overloaded
                state, this leaf is set to zero.";
        }
    } //notification
    notification pcep-session-peer-overload-clear {
        description
            "This notification is sent when a peer leaves overload
            state.";
        uses notification-instance-hdr;
        leaf peer-overloaded {
            type boolean;
            description
                "If the peer has informed the local PCEP entity that
                it is currently overloaded, then this is set to
                true. Otherwise, it is set to false.";
        }
    } //notification
    /*
     * RPC
     */
    rpc trigger-resync {
        if-feature stateful;
        if-feature stateful-sync-opt;
        description
            "Trigger the resyncrinization at the PCE";
        input {
            leaf pcc {
                type leafref {
                    path "/pcep-state/entity/peers/peer/addr";
                }
            description
                "The IP address to identify the PCC. The state
                 syncronization is re-triggered for all LSPs from
                 the PCC. The rpc on the PCC will be ignored.";
            }
        }
    }//rpc
}//module
