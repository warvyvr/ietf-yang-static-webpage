module ietf-dots-signal {
      namespace "urn:ietf:params:xml:ns:yang:ietf-dots-signal";
      prefix "signal";
      import ietf-inet-types {
          prefix "inet";
      }
     organization "Cisco Systems, Inc.";
     contact "Tirumaleswar Reddy <tireddy@cisco.com>";

     description
       "This module contains YANG definition for DOTS
       signal sent by the DOTS client to the DOTS server";

     revision 2016-11-28 {
       reference
       "https://tools.ietf.org/html/draft-reddy-dots-signal-channel";
     }

     container mitigation-scope {

          description "top level container for mitigation request";
          list scope {
             key mitigation-id;
             description "Identifier for the mitigation request";
             leaf mitigation-id {
                type int32;
                description "mitigation request identifier";
              }
              leaf-list target-ip {
                  type inet:ip-address;
                  description "IP address";
              }
              leaf-list target-prefix {
                  type inet:ip-prefix;
                  description "prefix";
              }
              list target-port-range {
                  key "lower-port upper-port";
                  description "Port range. When only lower-port is present,
                               it represents a single port.";
                  leaf lower-port {
                     type inet:port-number;
                     mandatory true;
                     description "lower port";
                  }
                  leaf upper-port {
                     type inet:port-number;
                         must ". >= ../lower-port" {
                           error-message
                           "The upper-port must be greater than or
                            equal to lower-port";
                         }
                         description "upper port";
                  }
              }
              leaf-list target-protocol {
                  type uint8;
                  description "Internet Protocol number";
              }
              leaf-list FQDN {
                   type inet:domain-name;
                   description "FQDN";
              }
              leaf-list URI {
                  type inet:uri;
                  description "URI";
              }
              leaf-list alias {

                  type string;
                  description "alias name";
              }
              leaf lifetime {
                  type int32;
                  description "lifetime";
              }
          }
     }
  }
