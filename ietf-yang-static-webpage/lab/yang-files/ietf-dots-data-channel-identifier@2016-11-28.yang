module ietf-dots-data-channel-identifier {
      namespace "urn:ietf:params:xml:ns:yang:ietf-dots-data-channel-identifier";
      prefix "alias";
      import ietf-inet-types {
          prefix "inet";
      }

     organization "McAfee, Inc.";
     contact "Konda, Tirumaleswar Reddy <TirumaleswarReddy_Konda@McAfee.com>";

     description
       "This module contains YANG definition for
        configuring identifiers for resources using DOTS data channel";

     revision 2016-11-28 {
       reference
       "https://tools.ietf.org/html/draft-reddy-dots-data-channel";
     }

     container identifier {
          description "top level container for identifiers";
              list alias {
                   key alias-name;
                   description "list of identifiers";
                   leaf alias-name {
                      type string;
                      description "alias name";
                   }
                   leaf-list ip {
                      type inet:ip-address;
                      description "IP address";
                   }
                   leaf-list prefix {
                      type inet:ip-prefix;
                      description "prefix";
                   }
                   list port-range {
                      key "lower-port upper-port";
                      description
                           "Port range. When only lower-port is present,
                            it represents a single port.";
                      leaf lower-port {
                         type inet:port-number;
                         mandatory true;
                         description "lower port";
                      }
                      leaf upper-port {
                         type inet:port-number;
                         must ". >= ../lower-port" {
                           error-message
                           "The upper-port must be greater than or
                            equal to lower-port";
                         }
                         description "upper port";
                      }

                   }
                   leaf-list traffic-protocol {
                      type uint8;
                      description "Internet Protocol number";
                   }
                   leaf-list fqdn {
                     type inet:domain-name;
                     description "FQDN";
                   }
                   leaf-list uri {
                     type inet:uri;
                     description "URI";
                   }
              }
     }
  }
